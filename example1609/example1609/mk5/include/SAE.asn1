-- Use of this module defined in SAE J2540/2
-- Latest document release for this module is Dec 2020
-- Filename: J2540-2-J2540ITIS-2024-rel-v1.1.1.asn
--

J2540ITIS
{joint-iso-itu-t(2) country (16) us (840) organization (1) sae (114566)
v2x-communications (1) technical-committees (1) v2x-core (5) standards (1)
itis-phrase-lists (2540) part-2 (2) asn1 (1)
major-version-1 (1) minor-version-1 (1)}

DEFINITIONS AUTOMATIC TAGS ::=
BEGIN

AccidentsAndIncidents ::= INTEGER  {
   -- Accidents
   accident                               (513),  -- Use when no further data is
                                                  -- available regarding involved vehicle
                                                  -- type
   serious-accident                       (514),
   injury-accident                        (515),
   minor-accident                         (516),
   multi-vehicle-accident                 (517),  -- To be used when events are NOT
                                                  -- distributed along a road segment
                                                  -- (i.e., one location)
   numerous-accidents                     (518),  -- To be used when events are
                                                  -- distributed along a road segment
   accident-involving-a-bicycle           (519),
   accident-involving-a-bus               (520),
   accident-involving-a-motorcycle        (521),
   accident-involving-a-pedestrian        (522),
   accident-involving-a-train             (523),
   accident-involving-a-truck             (524),
   accident-involving-a-semi-trailer      (562),
   accident-involving-hazardous-materials (525),
   earlier-accident                       (526),  -- Hint: Typically used as a cause, as
                                                  -- with "Due to"
   medical-emergency                      (527),
   secondary-accident                     (528),
   rescue-and-recovery-work-REMOVED       (529),  -- Removed, use Rescue and recovery
                                                  -- work in progress in the Incident
                                                  -- Response Status group when needed
   accident-investigation-work            (530),
   incident                               (531),  -- Hint: For non-accident incidents
                                                  -- (disabled, police pull over, etc.)
                                                  -- where no further information is
                                                  -- available
   -- Disabled, etc.
   stalled-vehicle                        (532),
   abandoned-vehicle                      (533),
   disabled-vehicle                       (534),
   disabled-truck                         (535),
   disabled-semi-trailer                  (536),  -- Alternative Rendering: disabled
                                                  -- tractor-trailer
   disabled-bus                           (537),
   disabled-train                         (538),
   vehicle-spun-out                       (539),
   vehicle-on-fire                        (540),
   vehicle-in-water                       (541),
   vehicles-slowing-to-look-at-accident   (542),  -- Alternative Rendering: On-looker
                                                  -- slowdown, Rubbernecking
   -- Jackknifed
   jackknifed-semi-trailer                (543),  -- Alternatives can use: jackknifed
                                                  -- tractor-trailer, jackknifed truck,
                                                  -- jackknifed big-rig
   jackknifed-trailer-home                (544),
   jackknifed-trailer                     (545),  -- Hint: Used for smaller trailers
                                                  -- (i.e., not type "jackknifed semi
                                                  -- trailer" above)
   -- Spills
   spillage-occurring-from-moving-vehicle (546),
   acid-spill                             (547),
   chemical-spill                         (548),
   fuel-spill                             (549),
   hazardous-materials-spill              (550),  -- Also use the Disaster lists for
                                                  -- large HAZMAT events
   oil-spill                              (551),
   spilled-load                           (552),
   toxic-spill                            (553),
   -- Overturned. Stuck
   overturned-vehicle                     (554),  -- Use when no further data is
                                                  -- available regarding involved vehicle
                                                  -- types
   overturned-truck                       (555),
   overturned-semi-trailer                (556),
   overturned-bus                         (557),
   derailed-train                         (558),
   stuck-vehicle                          (559),  -- It is preferred to provide data
                                                  -- which denotes WHY the vehicle is
                                                  -- stuck (i.e., mud/snow, under bridge,
                                                  -- too wide, etc.)
   truck-stuck-under-bridge               (560),  -- Alternative Rendering: high load
                                                  -- hit involving truck
   bus-stuck-under-bridge                 (561),  -- Alternative Rendering: high load
                                                  -- hit involving bus
   -- Cancel Types
   accident-cleared                       (638),
   incident-cleared                       (639)
   } (0..65535)

AlternateRoute ::= INTEGER  {
   detour-where-possible                           (8449),
   no-detour-available                             (8450),
   follow-signs                                    (8451),
   follow-detour-signs                             (8452),
   follow-special-detour-markers                   (8453),
   do-not-follow-detour-signs                      (8454),
   detour-in-operation                             (8455),
   follow-local-detour                             (8456),
   compulsory-detour-in-operation                  (8457),
   no-suitable-detour-available                    (8458),
   detour-is-no-longer-recommended                 (8459),
   local-drivers-are-recommended-to-avoid-the-area (8460),
   trucks-are-recommended-to-avoid-the-area        (8461),
   consider-alternate-route                        (8462),
   consider-alternate-parking                      (8463),
   consider-alternate-destination                  (8464),
   consider-alternate-area                         (8465),
   -- Specific Route Types
   snow-route                                      (8466),
   emergency-snow-route                            (8467),
   evacuation-route                                (8468),  -- May be preceded by a
                                                            -- specific type, Used also
                                                            -- for general emergency
                                                            -- routes.
   truck-route                                     (8469),
   hazardous-materials-route                       (8470),  -- May be used with 'any
                                                            -- time' for allowed, or 'no'
                                                            -- for prohibited, or
                                                            -- 'detour'
   detour                                          (8471)
   } (0..65535)


AssetStatus ::= INTEGER  {
   unknown-status       (10240),  -- Used when status is not known
   ready-for-use        (10241),
   working-normally     (10242),
   working-autonomously (10243),
   working-incorrectly  (10244),
   not-working          (10245),
   normal-maintenance   (10246),
   in-route-to-use      (10247),
   returning-from-use   (10248),
   out-of-service       (10249),
   off-duty             (10250),
   on-patrol            (10251),
   on-call              (10252),
   on-break             (10253),
   mandatory-time-off   (10254),
   low-on-fuel          (10255),
   low-on-water         (10256),
   low-charge           (10257),
   missing              (10258)   -- Use "sign down" in device status if an object is
                                  -- damaged (or use "damaged") and could be returned to
                                  -- service, use "missing" only if an object is in fact
                                  -- missing
   } (0..65535)


Closures ::= INTEGER  {
   closed-to-traffic      (769),  -- Used for road-closed and variations
   closed                 (770),  -- Hint: use this only for NON road-lane items (such as
                                  -- a rest stop)
   closed-ahead           (771),
   closed-intermittently  (772),
   closed-for-repairs     (773),
   closed-for-the-season  (774),
   blocked                (775),
   blocked-ahead          (776),
   reduced-to-one-lane    (777),
   reduced-to-two-lanes   (778),
   reduced-to-three-lanes (779),
   collapse               (780),  -- Used with bridges and tunnels
   out                    (781),  -- Used with bridges and roads
   -- Cancel Types
   open-to-traffic        (891),
   open                   (892),  -- Hint: use this only for NON road-lane items (such as
                                  -- a rest stop)
   reopened-to-traffic    (893),
   clearing               (894),
   cleared-from-road      (895)
   } (0..65535)
   -- Combine with lane-roadway (or generic locations) as needed to form things like
   -- "toll lane closed ahead"


DelayStatusCancellation ::= INTEGER  {
   -- Delays
   delays                             (1537),
   short-delays                       (1538),
   long-delays                        (1539),
   very-long-delays                   (1540),
   delays-of-uncertain-duration       (1541),
   delayed-until-further-notice       (1542),
   busy                               (1543),  -- Hint: Combine with generic locations
                                               -- (station busy, etc.)
   very-busy                          (1544),
   crowded                            (1545),
   overcrowded                        (1546),
   -- Cancellations
   cancellations                      (1547),
   route-canceled-and-no-replacement (1548),
   service-canceled                  (1549),
   service-suspended                  (1550),
   service-withdrawn                  (1551),
   service-fully-booked               (1552),
   all-services-fully-booked          (1553),
   -- Service Levels
   next-departure                     (1554),  -- Typically followed by a time value
   next-arrival                       (1555),  -- Typically followed by a # value of time
   very-frequent-service              (1556),
   frequent-service                   (1557),
   fairly-frequent-service            (1558),
   regular-service                    (1559),
   irregular-service                  (1560),
   not-operating                      (1561),
   -- Other
   system-busy                        (1562),  -- In this context "system" means the
                                               -- entire network of services over a wide
                                               -- area such as an airline system
   system-very-busy                   (1563),
   system-crowded                     (1564),
   system-overcrowded                 (1565),
   deleted-travel-time                (1566),  -- A duplicate entry, now removed in favor
                                               -- of item 269
   headway                            (1567),  -- Typically followed by a # value of time
   extra-services-in-operation        (1568),
   -- Cancel Types
   delays-clearing                    (1660),
   delays-cleared                     (1661),
   normal-services-resumed            (1662),
   operating                          (1663)   -- Use operating for "services" such as
                                               -- bus service
   } (0..65535)


DeviceStatus ::= INTEGER  {
   lane-control-signs-not-working                   (2305),
   lane-control-signs-working-incorrectly           (2306),
   lane-control-signs-operating                     (2307),
   variable-message-signs-not-working               (2308),
   variable-message-signs-working-incorrectly       (2309),
   variable-message-signs-operating                 (2310),
   emergency-telephones-not-working                 (2311),
   emergency-telephone-number-not-working           (2312),
   traffic-lights-not-working                       (2313),
   traffic-lights-working-incorrectly               (2314),
   ramp-control-signals-not-working                 (2315),
   ramp-control-signals-working-incorrectly         (2316),
   temporary-traffic-lights-not-working             (2317),
   temporary-traffic-lights-working-incorrectly     (2318),
   traffic-signal-control-computer-not-working      (2319),
   traffic-signal-timings-changed                   (2320),
   overheight-warning-system-triggered              (2321),
   equipment-failure                                (2322),
   railroad-crossing-equipment-failure              (2323),
   tunnel-ventilation-not-working                   (2324),
   power-failure                                    (2325),  -- Hint: Use for localized
                                                             -- cases of power loss
   widespread-power-outages                         (2326),  -- Alternative  rendering:
                                                             -- widespread power cuts
   technical-problems                               (2327),
   sign-down                                        (2328),
   lines-in-road-faded                              (2329),
   damaged-light-standard                           (2330),  -- Used for all forms of
                                                             -- pole/support damage
   traffic-signal-stuck-on-flash                    (2331),
   guide-rail                                       (2332),  -- Used for barriers as well
   fencing                                          (2333),
   light-standard-hanging-by-wires                  (2334),
   call-box                                         (2335),
   signal-cabinet                                   (2336),  -- Use for all types of
                                                             -- equipment cabinets
   detector                                         (2337),  -- All forms of vehicle
                                                             -- detectors
   improper-use-of-State-vehicle-or-equipment       (2338),
   bulb-out                                         (2339),
   not-yet-operational                              (2340),  -- When installed but not
                                                             -- yet brought on-line for
                                                             -- use by the system
   not-yet-installed                                (2341),  -- When planned
   -- Cancel Types
   electronic-signs-repaired                        (2428),
   emergency-call-facilities-restored               (2429),
   traffic-signals-repaired                         (2430),
   railroad-crossing-equipment-now-working-normally (2431)
   } (0..65535)


Disasters ::= INTEGER  {
   -- Water Related
   flash-flood                       (3073),
   major-flood                       (3074),
   reservoir-failure                 (3075),
   levee-failure                     (3076),
   tsunami                           (3077),
   tidal-wave                        (3078),
   -- Fire Related
   volcanic-eruption                 (3079),
   ash-fall                          (3080),
   lava-flow                         (3081),
   serious-fire                      (3082),
   forest-fire                       (3083),
   wildfire                          (3084),
   building-fire                     (3085),
   brush-fire                        (3086),
   grass-fire                        (3087),
   fire-danger-extreme               (3088),
   fire-danger-very-high             (3089),
   fire-danger-high                  (3090),
   fire-danger-medium                (3091),
   fire-danger-low                   (3092),
   --  Other
   earthquake-damage                 (3093),
   air-crash                         (3094),
   rail-crash                        (3095),
   toxic-release                     (3096),
   toxic-leak                        (3097),
   radioactive-release               (3098),
   radiation-hazard                  (3099),
   reactor-leakage                   (3100),
   explosion                         (3101),
   major-hazardous-materials-fire    (3102),  -- Alternative Rendering: Major HAZMAT
                                              -- fire
   major-hazardous-materials-release (3103),  -- Alternative Rendering: Major HAZMAT
                                              -- release
   -- Cancel Types
   disaster-cleared                  (3199)
   } (0..65535)


Disturbances ::= INTEGER  {
   assault                            (3329),  -- This index is not to be used as a
                                               -- default value for this category
   crime                              (3330),
   robbery                            (3331),
   fare-dispute                       (3332),
   shooting                           (3333),
   gunfire-on-roadway                 (3334),
   suicide                            (3335),
   fight                              (3336),  -- Involves a few  persons and is
                                               -- localized (alt: brawl)
   gang-fight                         (3337),  -- Multi-party event occurring which may
                                               -- involve weapons
   person-harassment                  (3338),  -- "person" may be rendered as "passenger"
                                               -- if used in a controlled environment
                                               -- such as transit
   person-injured                     (3339),
   sick-customer                      (3363),
   unruly-passenger                   (3340),
   person-intoxicated                 (3341),
   crowd-control-problem              (3342),
   demonstration                      (3343),
   march                              (3344),
   public-disturbance                 (3345),
   riot                               (3346),
   civil-unrest                       (3347),
   civil-emergency                    (3348),
   strike                             (3349),
   public-transit-strike              (3350),  -- Hint: Strike affecting services
   stampede                           (3351),
   teargas-used                       (3352),
   security-alert                     (3353),  -- Heightened security procedures in
                                               -- effect
   security-incident                  (3354),
   checkpoint                         (3355),
   bomb-alert                         (3356),
   terrorist-incident                 (3357),
   high-velocity-shell-fire           (3358),  -- Hint: Used as a part of avalanche
                                               -- control
   explosives-in-use                  (3359),
   air-raid                           (3360),
   weapons-of-mass-destruction-threat (3361),
   military-operations                (3362),  -- (war)
   -- Cancel Types
   security-problem-cleared           (3454),
   traffic-disturbance-cleared        (3455)
   } (0..65535)
   -- Disturbances occurring on or affecting the actual roadway or surrounding areas


GenericLocations ::= INTEGER  {
   -- Road Related
   on-bridges                  (7937),  -- Not to be used as the default for this
                                        -- category
   in-tunnels                  (7938),
   entering-or-leaving-tunnels (7939),
   on-ramps                    (7940),
   in-road-construction-area   (7941),
   around-a-curve              (7942),
   on-curve                    (8026),
   on-tracks                   (8009),
   in-street                   (8025),  -- As in in-street pad crossing
   shoulder                    (8027),
   on-minor-roads              (7943),
   in-the-opposing-lanes       (7944),
   adjacent-to-roadway         (7945),
   across-tracks               (8024),
   on-bend                     (7946),
   intersection                (8032),
   entire-intersection         (7947),
   in-the-median               (7948),
   moved-to-side-of-road       (7949),
   moved-to-shoulder           (7950),
   on-the-roadway              (7951),  -- Use generic locations and groups affected to
                                        -- make other such phrases
   dip                         (8010),
   traffic-circle              (8011),  -- Used for W2-6 graphic as well. Alt term:
                                        -- roundabout
   crossover                   (8028),
   cross-road                  (8029),  -- Also used for W2-1 Note that in some uses
                                        -- this is one word
   side-road                   (8030),  -- Do not used for W2-2R and W2-2L
   to                          (8014),
   by                          (8015),
   through                     (8016),
   area-of                     (8017),  -- Also area
   under                       (8018),
   over                        (8019),
   from                        (8020),
   approaching                 (8021),
   entering-at                 (8022),  -- Alt form: Entrance
   exiting-at                  (8023),
   -- Terrain & Geography
   in-shaded-areas             (7952),
   in-low-lying-areas          (7953),
   in-the-downtown-area        (7954),
   in-the-inner-city-area      (7955),
   in-parts                    (7956),
   in-some-places              (7957),
   in-the-ditch                (7958),
   in-the-valley               (7959),
   on-hill-top                 (7960),
   near-the-foothills          (7961),
   at-high-altitudes           (7962),
   near-the-lake               (7963),
   near-the-shore              (7964),
   nearby-basin                (8008),
   over-the-crest-of-a-hill    (7965),
   other-than-on-the-roadway   (7966),
   near-the-beach              (7967),
   near-beach-access-point     (7968),
   mountain-pass               (8006),
   lower-level                 (7969),
   upper-level                 (7970),
   coast                       (8034),
   -- Transit Travel, Air Travel and Places
   airport                     (7971),
   concourse                   (7972),
   gate                        (7973),
   baggage-claim               (7974),
   customs-point               (7975),
   reservation-center          (8007),
   station                     (7976),
   platform                    (7977),  -- Alternative Rendering: track
   dock                        (7978),
   depot                       (7979),
   ev-charging-point           (7980),
   information-welcome-point   (7981),  -- Use for Tourist Information as well (D9-10)
   at-rest-area                (7982),
   at-service-area             (7983),
   at-weigh-station            (7984),
   roadside-park               (8033),
   picnic-areas                (7985),
   rest-area                   (7986),
   service-stations            (7987),
   toilets                     (7988),  -- Note also rest rooms in structures
   bus-stop                    (8031),
   park-and-ride-lot           (8012),  -- Not to be used as a mode of travel
   -- Direction of Travel
   on-the-right                (7989),
   on-the-left                 (7990),
   in-the-center               (7991),
   in-the-opposite-direction   (7992),
   cross-traffic               (7993),
   northbound-traffic          (7994),
   eastbound-traffic           (7995),
   southbound-traffic          (7996),
   westbound-traffic           (7997),
   -- Compass Points
   north                       (7998),
   south                       (7999),
   east                        (8000),
   west                        (8001),
   northeast                   (8002),
   northwest                   (8003),
   southeast                   (8004),
   southwest                   (8005)
   } (0..65535)


IncidentResponseEquipment ::= INTEGER  {
   ground-fire-suppression          (9985),
   heavy-ground-equipment           (9986),
   aircraft                         (9988),
   marine-equipment                 (9989),
   support-equipment                (9990),
   medical-rescue-unit              (9991),
   other                            (9993),   -- Depreciated by fire standards, do not
                                              -- use
   ground-fire-suppression-other    (9994),
   engine                           (9995),
   truck-or-aerial                  (9996),
   quint                            (9997),   -- A five-function type of fire apparatus.
                                              -- The units in the movie Backdraft were
                                              -- quints
   tanker-pumper-combination        (9998),
   brush-truck                      (10000),
   aircraft-rescue-firefighting     (10001),
   heavy-ground-equipment-other     (10004),
   dozer-or-plow                    (10005),
   tractor                          (10006),
   tanker-or-tender                 (10008),
   aircraft-other                   (10024),
   aircraft-fixed-wing-tanker       (10025),
   helitanker                       (10026),
   helicopter                       (10027),
   marine-equipment-other           (10034),
   fire-boat-with-pump              (10035),
   boat-no-pump                     (10036),
   support-apparatus-other          (10044),
   breathing-apparatus-support      (10045),
   light-and-air-unit               (10046),
   medical-rescue-unit-other        (10054),
   rescue-unit                      (10055),
   urban-search-rescue-unit         (10056),
   high-angle-rescue                (10057),
   crash-fire-rescue                (10058),
   bLS-unit                         (10059),
   aLS-unit                         (10060),
   mobile-command-post              (10075),  -- Deprecated, do not use
   chief-officer-car                (10076),
   hAZMAT-unit                      (10077),
   type-i-hand-crew                 (10078),
   type-ii-hand-crew                (10079),
   privately-owned-vehicle          (10083),  -- (Often found in volunteer fire teams)
   other-apparatus-resource         (10084),  -- (Remapped from fire code zero)
   ambulance                        (10085),
   bomb-squad-van                   (10086),
   combine-harvester                (10087),
   construction-vehicle             (10088),
   farm-tractor                     (10089),
   grass-cutting-machines           (10090),
   hAZMAT-containment-tow           (10091),
   heavy-tow                        (10092),
   light-tow                        (10094),
   flatbed-tow                      (10114),
   hedge-cutting-machines           (10093),
   mobile-crane                     (10095),
   refuse-collection-vehicle        (10096),
   resurfacing-vehicle              (10097),
   road-sweeper                     (10098),
   survey-crews                     (10115),
   roadside-litter-collection-crews (10099),
   salvage-vehicle                  (10100),
   sand-truck                       (10101),
   snowplow                         (10102),
   steam-roller                     (10103),
   swat-team-van                    (10104),
   track-laying-vehicle             (10105),
   unknown-vehicle                  (10106),
   white-lining-vehicle             (10107),  -- Consider using Roadwork "road marking
                                              -- operations" unless the objective is to
                                              -- refer to the specific vehicle of this
                                              -- type. Alternative Rendering: line
                                              -- painting vehicle
   dump-truck                       (10108),
   supervisor-vehicle               (10109),
   snow-blower                      (10110),
   rotary-snow-blower               (10111),
   road-grader                      (10112),  -- Alternative term: motor grader
   steam-truck                      (10113)   -- A special truck that thaws culverts and
                                              -- storm drains
   } (0..65535)


IncidentResponseStatus ::= INTEGER  {
   unconfirmed-report                   (2817),
   initial-response-en-route            (2818),
   follow-up-response-en-route          (2819),
   initial-response-on-scene            (2820),
   follow-up-response-on-scene          (2821),
   confirmed-report                     (2822),
   scene-is-unsecured-at-this-time      (2823),  -- Caution: This has different meanings
                                                 -- in Public Safety use
   response-scene-secured               (2824),  -- Caution: This has different meanings
                                                 -- in Public Safety use
   rescue-and-recovery-work-in-progress (2825),
   extraction-in-progress               (2826),
   clearance-work-in-progress           (2827),
   body-removal-operations              (2828),
   fire-containment-contained           (2829),
   fire-containment-not-contained       (2830),
   event-cleared                        (2831),  -- Meaning that responder has left
                                                 -- scene, not that surrounding traffic
                                                 -- has cleared to a normal level
   traffic-clearing                     (2832),
   incident-closed                      (2833)   -- A "case closed" meaning which can
                                                 -- differ considerably by local agency
                                                 -- policies
   } (0..65535)
   -- Primarily this list is used for exchanging response status with other agencies.
   -- Some of these phrases should be avoided in ITIS targeted for consumer use


SystemInformation ::= INTEGER  {
   information-available-on-radio         (4353),  -- Not to be used as a default for
                                                   -- this category D12-1
   information-available-on-TV            (4354),
   call-to-get-information                (4355),
   information-available-via-Internet     (4356),
   test-message                           (4357),  -- Not to be displayed on consumer
                                                   -- devices if possible
   no-information-available               (4358),  -- Typically combined with "on xxx
                                                   -- service" where xxx is a type of
                                                   -- service (bus, rail, etc.)
   null-description                       (4359),  -- (but with event location or other
                                                   -- information provided in the
                                                   -- message)
   police-assistance                      (4361),
   police-monitor-CB                      (4362),  -- D12-3
   emergency-notification                 (4363),
   in-emergency-dial-911                  (4364),  -- D12-14
   travel-Info-call-511                   (4365),  -- D`12-5
   car-pool-information                   (4366),  -- D12-2
   information-service-resumed            (4478),
   -- Cancel Types
   information-service-is-being-suspended (4360),
   message-canceled                       (4479)   -- Not Recommended for use
   } (0..65535)


AdviceInstructionsMandatory ::= INTEGER  {
   keep-to-the-right                    (7425),
   keep-to-the-left                     (7426),
   use-right-lane                       (7427),
   use-left-lane                        (7428),
   stay-in-lane                         (7450),
   merge                                (7451),  -- Typically followed by direction
                                                 -- left/right Used for W4-1R and W4-1L
   heavy-vehicles-use-right-lane        (7429),
   heavy-vehicles-use-left-lane         (7430),
   observe-signals                      (7431),
   observe-signs                        (7432),
   no-passing                           (7433),  -- Used for MUTCD signs
   no-smoking                           (7434),
   no-open-flames                       (7435),
   use-shoulder-as-lane                 (7436),
   do-not-drive-on-the-shoulder         (7437),
   allow-emergency-vehicles-to-pass     (7438),
   clear-a-lane-for-emergency-vehicles  (7439),
   pull-over-to-the-edge-of-the-roadway (7440),
   wait-for-escort-vehicle              (7441),
   in-emergency-wait-for-police-patrol  (7442),
   reduce-your-speed                    (7443),
   observe-speed-limits                 (7444),
   check-point                          (7445),
   entry-requirements                   (7446),
   insurance-requirements               (7447),
   firearms-requirements                (7448),
   pet-requirements                     (7449),
   slower-traffic-keep-right            (7452),
   keep-off                             (7453),  -- Typically followed by object
   evacuate-area-immediately            (7454),
   -- Cancel Types
   shoulder-travel-no-longer-allowed    (7547)
   } (0..65535)


AdviceInstructionsRecommendations ::= INTEGER  {
   drive-carefully                                             (7169),
   drive-with-extreme-caution                                  (7170),
   approach-with-care                                          (7171),
   keep-your-distance                                          (7172),
   increase-normal-following-distance                          (7173),
   test-your-brakes                                            (7174),
   cross-intersection-with-care                                (7175),
   pass-with-care                                              (7176),  -- Use as MUTCD
                                                                        -- sign
   pass                                                        (7200),  -- Used for
                                                                        -- passing
                                                                        -- action, as in
                                                                        -- do not pass
   use-low-beam-headlights                                     (7177),
   use-fog-lights                                              (7178),
   use-hazard-warning-lights                                   (7179),  -- Alternative
                                                                        -- Rendering:
                                                                        -- use blinkers
   do-not-leave-your-vehicle                                   (7180),
   leave-your-vehicle-and-proceed-to-next-safe-place           (7181),
   turn-off-engine                                             (7182),  -- Alternative
                                                                        -- Rendering:
                                                                        -- switch off
                                                                        -- engine
   close-all-windows-turn-off-heater-air-conditioner-and-vents (7183),
   turn-off-air-conditioner-to-prevent-engine-overheating      (7184),
   turn-off-mobile-phones-and-two-way-radios                   (7185),  -- Alternative
                                                                        -- Rendering:
                                                                        -- switch off
                                                                        -- mobile phones
                                                                        -- and two way
                                                                        -- radios
   prepare-to-stop                                             (7186),
   be-prepared-to-stop                                         (7201),
   stop-at-next-rest-area                                      (7187),
   stop-at-next-safe-place                                     (7188),
   only-travel-if-absolutely-necessary                         (7189),
   drive-to-another-service-area                               (7190),
   use-through-traffic-lanes                                   (7191),
   use-local-traffic-lanes                                     (7192),
   use-left-hand-parallel-roadway                              (7193),
   use-right-hand-parallel-roadway                             (7194),
   use-heavy-vehicle-lane                                      (7195),  -- Alternative
                                                                        -- Rendering:
                                                                        -- use truck
                                                                        -- lanes
   observe-recommended-speed                                   (7196),
   signals-sequenced-for-speed                                 (7202),  -- Typically
                                                                        -- followed by
                                                                        -- speed
   maintain-top-safe-speed                                     (7203),
   facing-traffic                                              (7197),
   push-button                                                 (7198),
   to-cross-street                                             (7199),
   evacuate-area-voluntarily                                   (7204),
   shelter-in-place                                            (7205)
   } (0..65535)


ITIStxt ::= IA5String (SIZE(1..500))

ITISgroups ::= INTEGER {
    trafficConditions                  (1),
    accidentsAndIncidents              (2),
    closures                           (3),
    roadwork                           (4),
    obstruction                        (5),
    delayStatusCancellation            (6),
    unusualDriving                     (7),
    mobileSituation                    (8),
    deviceStatus                       (9),
    restrictionClass                  (10),
    incidentResponseStatus            (11),
    disasters                         (12),
    disturbances                      (13),
    sportingEvents                    (14),
    specialEvents                     (15),
    parkingInformation                (16),
    systemInformation                 (17),
    weatherConditions                 (18),
    precipitation                     (19),
    winds                             (20),
    visibilityAndAirQuality           (21),
    temperature                       (22),
    pavementConditions                (23),
    winterDrivingRestrictions         (24),
    winterDrivingIndex                (25),
    suggestionAdvice                  (26),
    warningAdvice                     (27),
    adviceInstructionsRecommendations (28),
    adviceInstructionsMandatory       (29),
    qualifiers                        (30),
    genericLocations                  (31),
    laneRoadway                       (32),
    alternateRoute                    (33),
    units                             (34),
    transitMode                       (35),
    vehicleGroupAffected              (36),
    travelerGroupAffected             (37),
    responderGroupAffected            (38),
    incidentResponseEquipment         (39),
    assetStatus                       (40),
    roadsideAssets                    (41),
    transitOperations                 (42),
    objects                           (43),
    validManeuvers                    (44),
    largeNumbers                      (45),
    namedObjects                      (46),
    recreationalObjectsAndActivities  (47),
    regulatoryAndWarningSigns         (48),
    smallNumbers                      (49),
    states                            (50),
    structures                        (51),
    streetSuffixes                    (52),
    mUTCDLocations                    (53)
    } (0..255)


ITIScode ::= INTEGER  {
   -- Traffic Conditions
   stopped-traffic                            (257),
   stop-and-go-traffic                        (258),
   slow-traffic                               (259),
   heavy-traffic                              (260),
   traffic-building                           (261),
   long-queues                                (262),
   traffic-congestion                         (263),
   traffic-lighter-than-normal                (264),
   traffic-heavier-than-normal                (265),
   traffic-much-heavier-than-normal           (266),
   current-speed                              (267),    -- Typically followed by a value
                                                        -- entry and a units entry
                                                        -- (MPH/KPH)
   speed-limit                                (268),    -- Typically followed by a value
                                                        -- entry and a units entry
                                                        -- (MPH/KPH)
   travel-time                                (269),    -- Typically followed by a value
                                                        -- entry and a units entry
                                                        -- (seconds)
   merging-traffic                            (272),    -- Typically followed by
                                                        -- direction left/right. Can be
                                                        -- used for W4-1R and W4-1L signs
   contraflow                                 (273),    -- also referred to as counter-flow
   -- Cancel Types
   contraflow-canceled                        (378),
   traffic-flowing-freely                     (379),
   traffic-easing                             (380),    -- Alternative rendering: traffic
                                                        -- clearing
   traffic-returned-to-normal                 (381),
   no-problems-to-report                      (382),
   traffic-congestion-cleared                 (383),
   -- Accidents and Incidents
   -- Accidents
   accident                                   (513),    -- Use when no further data is
                                                        -- available regarding involved
                                                        -- vehicle type
   serious-accident                           (514),
   injury-accident                            (515),
   minor-accident                             (516),
   multi-vehicle-accident                     (517),    -- To be used when events are NOT
                                                        -- distributed along a road
                                                        -- segment (i.e., one location)
   numerous-accidents                         (518),    -- To be used when events are
                                                        -- distributed along a road
                                                        -- segment
   accident-involving-a-bicycle               (519),
   accident-involving-a-bus                   (520),
   accident-involving-a-motorcycle            (521),
   accident-involving-a-pedestrian            (522),
   accident-involving-a-train                 (523),
   accident-involving-a-truck                 (524),
   accident-involving-a-semi-trailer          (562),
   accident-involving-hazardous-materials     (525),
   earlier-accident                           (526),    -- Hint: Typically used as a
                                                        -- cause, as with "Due to"
   medical-emergency                          (527),
   secondary-accident                         (528),
   rescue-and-recovery-work-REMOVED           (529),    -- Removed, use Rescue and
                                                        -- recovery work in progress in
                                                        -- the Incident Response Status
                                                        -- group when needed
   accident-investigation-work                (530),
   incident                                   (531),    -- Hint: For non-accident
                                                        -- incidents (disabled, police
                                                        -- pull over, etc.) where no
                                                        -- further information is
                                                        -- available
   -- Disabled, etc.
   stalled-vehicle                            (532),
   abandoned-vehicle                          (533),
   disabled-vehicle                           (534),
   disabled-truck                             (535),
   disabled-semi-trailer                      (536),    -- Alternative Rendering:
                                                        -- disabled tractor-trailer
   disabled-bus                               (537),
   disabled-train                             (538),
   vehicle-spun-out                           (539),
   vehicle-on-fire                            (540),
   vehicle-in-water                           (541),
   vehicles-slowing-to-look-at-accident       (542),    -- Alternative Rendering:
                                                        -- On-looker slowdown,
                                                        -- Rubbernecking
   -- Jackknifed
   jackknifed-semi-trailer                    (543),    -- Alternatives can use:
                                                        -- jackknifed tractor-trailer,
                                                        -- jackknifed truck, jackknifed
                                                        -- big-rig
   jackknifed-trailer-home                    (544),
   jackknifed-trailer                         (545),    -- Hint: Used for smaller
                                                        -- trailers (i.e., not type
                                                        -- "jackknifed semi trailer"
                                                        -- above)
   -- Spills
   spillage-occurring-from-moving-vehicle     (546),
   acid-spill                                 (547),
   chemical-spill                             (548),
   fuel-spill                                 (549),
   hazardous-materials-spill                  (550),    -- Also use the Disaster lists
                                                        -- for large HAZMAT events
   oil-spill                                  (551),
   spilled-load                               (552),
   toxic-spill                                (553),
   -- Overturned. Stuck
   overturned-vehicle                         (554),    -- Use when no further data is
                                                        -- available regarding involved
                                                        -- vehicle types
   overturned-truck                           (555),
   overturned-semi-trailer                    (556),
   overturned-bus                             (557),
   derailed-train                             (558),
   stuck-vehicle                              (559),    -- It is preferred to provide
                                                        -- data which denotes WHY the
                                                        -- vehicle is stuck (i.e.,
                                                        -- mud/snow, under bridge, too
                                                        -- wide, etc.)
   truck-stuck-under-bridge                   (560),    -- Alternative Rendering: high
                                                        -- load hit involving truck
   bus-stuck-under-bridge                     (561),    -- Alternative Rendering: high
                                                        -- load hit involving bus
   -- Cancel Types
   accident-cleared                           (638),
   incident-cleared                           (639),
   -- Closures (Road and Lane)
   closed-to-traffic                          (769),    -- Used for road-closed and
                                                        -- variations
   closed                                     (770),    -- Hint: use this only for NON
                                                        -- road-lane items (such as a
                                                        -- rest stop)
   closed-ahead                               (771),
   closed-intermittently                      (772),
   closed-for-repairs                         (773),
   closed-for-the-season                      (774),
   blocked                                    (775),
   blocked-ahead                              (776),
   reduced-to-one-lane                        (777),
   reduced-to-two-lanes                       (778),
   reduced-to-three-lanes                     (779),
   collapse                                   (780),    -- Used with bridges and tunnels
   out                                        (781),    -- Used with bridges and roads
   -- Cancel Types
   open-to-traffic                            (891),
   open                                       (892),    -- Hint: use this only for NON
                                                        -- road-lane items (such as a
                                                        -- rest stop)
   reopened-to-traffic                        (893),
   clearing                                   (894),
   cleared-from-road                          (895),
   -- Roadwork
   -- Roads
   road-construction                          (1025),   -- Alt text: Road Work
   major-road-construction                    (1026),
   long-term-road-construction                (1027),
   construction-work                          (1028),
   paving-operations                          (1029),
   work-in-the-median                         (1030),
   road-reconstruction                        (1031),
   opposing-traffic                           (1032),
   narrow-lanes                               (1033),
   construction-traffic-merging               (1034),
   single-line-traffic-alternating-directions (1035),
   road-maintenance-operations                (1036),
   road-marking-operations                    (1037),
   road-widening                              (1061),   -- Used for roadwork, not as an
                                                        -- MUTCD sign
   cracks                                     (1052),   -- Used for disjoint roadway
                                                        -- surface
   crack-REMOVE                               (1058),   -- No Longer Used. Used for
                                                        -- disjoint roadway surface
   bumps                                      (1053),   -- Used for swelling
   drop-off                                   (1059),
   storm-drain                                (1054),
   -- Bridges
   bridge-maintenance-operations              (1038),
   bridge-construction                        (1039),
   bridge-demolition-work                     (1040),
   seismic-retrofit                           (1060),   -- All types of earthquake
                                                        -- construction
   -- Other
   overgrown-grass                            (1055),
   overgrown-brushshrubs                      (1056),
   overgrown-trees                            (1057),
   blasting                                   (1041),   -- See also: avalanche
   avalanche-control-activities               (1042),
   water-main-work                            (1043),
   gas-main-work                              (1044),
   work-on-underground-cables                 (1045),
   work-on-underground-services               (1046),
   new-road-construction-layout               (1047),
   new-road-layout                            (1048),
   temporary-lane-markings                    (1049),
   temporary-traffic-lights                   (1050),
   emergency-maintenance                      (1051),
   utility-work                              (1062),
   -- Cancel Types
   road-maintenance-cleared                   (1146),
   normal-road-layout-restored                (1147),
   road-work-clearance-in-progress            (1148),
   road-construction-cleared                  (1149),
   normal-traffic-lanes-restored              (1150),
   road-work-cleared                          (1151),
   -- Obstructions
   -- General
   obstruction-on-roadway                     (1281),
   object-on-roadway                          (1282),
   objects-falling-from-moving-vehicle        (1283),
   debris-on-roadway                          (1284),
   storm-damage                               (1285),
   -- People
   people-on-roadway                          (1286),
   bicyclists-on-roadway                      (1287),
   sightseers-obstructing-access              (1288),
   large-numbers-of-visitors                  (1289),
   -- Animals
   animal-on-roadway                          (1290),
   large-animal-on-roadway                    (1291),
   herd-of-animals-on-roadway                 (1292),
   animal-struck                              (1293),
   -- Specific Items
   advertising-signs                          (1315),   -- Used for illegal signage as
                                                        -- well
   fallen-trees                               (1294),
   over-turned-trees                          (1311),
   tree-limbs                                 (1312),
   utility-pole-down                          (1314),
   downed-power-lines                         (1295),   -- Alternative Rendering: fallen
                                                        -- power lines
   downed-cables                              (1296),   -- Alternative Rendering: fallen
                                                        -- cables
   subsidence                                 (1297),   -- Alternative Rendering: road
                                                        -- collapse
   road-surface-collapse                      (1298),
   frost-jacking                              (1317),   -- A unique Alaska problem caused
                                                        -- by culverts or other features
                                                        -- jacking out of ground due to
                                                        -- freezing
   frost-heave                                (1316),   -- A large standing wave of soil
                                                        -- under pavement due to frost
                                                        -- action
   pavement-buckled                           (1299),
   pothole                                    (1300),
   flooding                                   (1301),
   broken-water-main                          (1302),
   collapsed-sewer                            (1303),
   wash-out                                   (1319),   -- What can happen to roads
   washboard                                  (1318),   -- A term for rough road or
                                                        -- unpaved roads
   sewer-overflow                             (1304),
   gas-leak                                   (1305),
   snowmelt                                   (1306),   -- Hint: Typically used as a
                                                        -- cause
   mudslide                                   (1307),
   avalanche                                  (1308),   -- Possibly a disaster as well
   rockfall                                   (1309),
   landslide                                  (1310),
   -- Cancel Types
   clearance-work                             (1406),
   obstruction-cleared                        (1407),
   -- Delays, Status, and Cancellations
   -- Delays
   delays                                     (1537),
   short-delays                               (1538),
   long-delays                                (1539),
   very-long-delays                           (1540),
   delays-of-uncertain-duration               (1541),
   delayed-until-further-notice               (1542),
   busy                                       (1543),   -- Hint: Combine with generic
                                                        -- locations (station busy, etc.)
   very-busy                                  (1544),
   crowded                                    (1545),
   overcrowded                                (1546),
   -- Cancellations
   cancellations                              (1547),
   route-canceled-and-no-replacement         (1548),
   service-canceled                          (1549),
   service-suspended                          (1550),
   service-withdrawn                          (1551),
   service-fully-booked                       (1552),
   all-services-fully-booked                  (1553),
   -- Service Levels
   next-departure                             (1554),   -- Typically followed by a time
                                                        -- value
   next-arrival                               (1555),   -- Typically followed by a #
                                                        -- value of time
   very-frequent-service                      (1556),
   frequent-service                           (1557),
   fairly-frequent-service                    (1558),
   regular-service                            (1559),
   irregular-service                          (1560),
   not-operating                              (1561),
   -- Other
   system-busy                                (1562),   -- In this context "system" means
                                                        -- the entire network of services
                                                        -- over a wide area such as an
                                                        -- airline system
   system-very-busy                           (1563),
   system-crowded                             (1564),
   system-overcrowded                         (1565),
   deleted-travel-time                        (1566),   -- A duplicate entry, now removed
                                                        -- in favor of item 269
   headway                                    (1567),   -- Typically followed by a #
                                                        -- value of time
   extra-services-in-operation                (1568),
   -- Cancel Types
   delays-clearing                            (1660),
   delays-cleared                             (1661),
   normal-services-resumed                    (1662),
   operating                                  (1663),   -- Use operating for "services"
                                                        -- such as bus service
   -- Unusual Driving
   vehicle-traveling-wrong-way                (1793),
   reckless-driver                            (1794),   -- Alternative Rendering:
                                                        -- erratic driver
   prohibited-vehicle-on-roadway              (1795),
   emergency-vehicles-on-roadway              (1796),
   high-speed-emergency-vehicles              (1797),
   high-speed-chase                           (1798),
   -- Cancel Types
   dangerous-vehicle-warning-cleared          (1918),
   emergency-vehicle-warning-cleared          (1919),
   -- Mobile Situation
   abnormal-load                              (2049),
   wide-load                                  (2050),
   long-load                                  (2051),
   slow-vehicle                               (2052),
   farm-equipment                             (2053),
   horse-drawn-vehicles                       (2054),
   overheight-load                            (2055),
   overweight-load                            (2056),
   tracked-vehicle                            (2057),
   vehicle-carrying-hazardous-materials       (2058),
   slow-moving-maintenance-vehicle            (2059),   -- Hint: mowing, line stripping,
                                                        -- sweepers, etc.
   convoy                                     (2060),
   military-convoy                            (2061),
   refugee-convoy                             (2062),
   motorcade                                  (2063),
   mobile-situation-repositioning             (2064),
   winter-maintenance-vehicles                (2065),
   snowplows                                  (2066),
   -- Cancel Types
   slow-moving-maintenance-vehicle-warning-cleared (2172),
   exceptional-load-warning-cleared           (2173),
   hazardous-load-warning-cleared             (2174),
   convoy-cleared                             (2175),
   -- Device and Equipment Status
   lane-control-signs-not-working             (2305),
   lane-control-signs-working-incorrectly     (2306),
   lane-control-signs-operating               (2307),
   variable-message-signs-not-working         (2308),
   variable-message-signs-working-incorrectly (2309),
   variable-message-signs-operating           (2310),
   emergency-telephones-not-working           (2311),
   emergency-telephone-number-not-working     (2312),
   traffic-lights-not-working                 (2313),
   traffic-lights-working-incorrectly         (2314),
   ramp-control-signals-not-working           (2315),
   ramp-control-signals-working-incorrectly   (2316),
   temporary-traffic-lights-not-working       (2317),
   temporary-traffic-lights-working-incorrectly (2318),
   traffic-signal-control-computer-not-working (2319),
   traffic-signal-timings-changed             (2320),
   overheight-warning-system-triggered        (2321),
   equipment-failure                          (2322),
   railroad-crossing-equipment-failure        (2323),
   tunnel-ventilation-not-working             (2324),
   power-failure                              (2325),   -- Hint: Use for localized cases
                                                        -- of power loss
   widespread-power-outages                   (2326),   -- Alternative  rendering:
                                                        -- widespread power cuts
   technical-problems                         (2327),
   sign-down                                  (2328),
   lines-in-road-faded                        (2329),
   damaged-light-standard                     (2330),   -- Used for all forms of pole/
                                                        -- support damage
   traffic-signal-stuck-on-flash              (2331),
   guide-rail                                 (2332),   -- Used for barriers as well
   fencing                                    (2333),
   light-standard-hanging-by-wires            (2334),
   call-box                                   (2335),
   signal-cabinet                             (2336),   -- Use for all types of equipment
                                                        -- cabinets
   detector                                   (2337),   -- All forms of vehicle detectors
   improper-use-of-State-vehicle-or-equipment (2338),
   bulb-out                                   (2339),
   not-yet-operational                        (2340),   -- When installed but not yet
                                                        -- brought on-line for use by the
                                                        -- system
   not-yet-installed                          (2341),   -- When planned
   -- Cancel Types
   electronic-signs-repaired                  (2428),
   emergency-call-facilities-restored         (2429),
   traffic-signals-repaired                   (2430),
   railroad-crossing-equipment-now-working-normally (2431),
   -- Restrictions
   restrictions                               (2561),
   ramp-restrictions                          (2562),
   truck-restriction                          (2563),
   speed-restriction                          (2564),   -- Used for required speeds, not
                                                        -- advised speeds
   noise-restriction                          (2565),
   traffic-regulations-have-been-changed      (2566),
   local-access-only                          (2567),
   no-trailers                                (2568),
   no-high-profile-vehicles                   (2569),
   hazardous-materials-truck-restriction      (2570),
   no-through-traffic                         (2571),
   no-motor-vehicles                          (2572),
   width-limit                                (2573),   -- Typically followed by a number
                                                        -- and unit value
   height-limit                               (2574),   -- Typically followed by a number
                                                        -- and unit value
   length-limit                               (2575),   -- Typically followed by a number
                                                        -- and unit value
   axle-load-limit                            (2576),   -- Typically followed by a number
                                                        -- and unit value
   gross-weight-limit                         (2577),   -- Typically followed by a number
                                                        -- and unit value
   axle-count-limit                           (2578),   -- Typically followed by a number
                                                        -- and unit value
   carpool-lane-available                     (2579),
   carpool-restrictions-changed               (2580),
   hOV-2-no-single-occupant-vehicles          (2581),
   hOV-3-no-vehicles-with-less-than-three-occupants (2582),
   bus-lane-available-for-all-vehicles        (2583),
   truck-lane-available-for-all-vehicles      (2584),
   permits-call-in-basis                      (2585),
   permits-temporarily-closed                 (2586),
   permits-closed                             (2587),
   road-use-permits-required                  (2588),
   -- Cancel Types
   permits-open                               (2675),
   restrictions-for-high-profile-vehicles-lifted (2676),
   width-limit-lifted                         (2677),
   height-limit-lifted                        (2678),
   length-limit-lifted                        (2679),
   axle-load-limit-lifted                     (2680),
   weight-limit-lifted                        (2681),
   axle-count-limit-lifted                    (2682),
   carpool-restrictions-lifted                (2683),
   lane-restrictions-lifted                   (2684),
   ramp-restrictions-lifted                   (2685),
   motor-vehicle-restrictions-lifted          (2686),
   restrictions-lifted                        (2687),
   -- Incident Response Status
   unconfirmed-report                         (2817),
   initial-response-en-route                  (2818),
   follow-up-response-en-route                (2819),
   initial-response-on-scene                  (2820),
   follow-up-response-on-scene                (2821),
   confirmed-report                           (2822),
   scene-is-unsecured-at-this-time            (2823),   -- Caution: This has different
                                                        -- meanings in Public Safety use
   response-scene-secured                     (2824),   -- Caution: This has different
                                                        -- meanings in Public Safety use
   rescue-and-recovery-work-in-progress       (2825),
   extraction-in-progress                     (2826),
   clearance-work-in-progress                 (2827),
   body-removal-operations                    (2828),
   fire-containment-contained                 (2829),
   fire-containment-not-contained             (2830),
   event-cleared                              (2831),   -- Meaning that responder has
                                                        -- left scene, not that
                                                        -- surrounding traffic has
                                                        -- cleared to a normal level
   traffic-clearing                           (2832),
   incident-closed                            (2833),   -- A "case closed" meaning which
                                                        -- can differ considerably by
                                                        -- local agency policies
   -- Disasters
   -- Water Related
   flash-flood                                (3073),
   major-flood                                (3074),
   reservoir-failure                          (3075),
   levee-failure                              (3076),
   tsunami                                    (3077),
   tidal-wave                                 (3078),
   -- Fire Related
   volcanic-eruption                          (3079),
   ash-fall                                   (3080),
   lava-flow                                  (3081),
   serious-fire                               (3082),
   forest-fire                                (3083),
   wildfire                                   (3084),
   building-fire                              (3085),
   brush-fire                                 (3086),
   grass-fire                                 (3087),
   fire-danger-extreme                        (3088),
   fire-danger-very-high                      (3089),
   fire-danger-high                           (3090),
   fire-danger-medium                         (3091),
   fire-danger-low                            (3092),
   --  Other
   earthquake-damage                          (3093),
   air-crash                                  (3094),
   rail-crash                                 (3095),
   toxic-release                              (3096),
   toxic-leak                                 (3097),
   radioactive-release                        (3098),
   radiation-hazard                           (3099),
   reactor-leakage                            (3100),
   explosion                                  (3101),
   major-hazardous-materials-fire             (3102),   -- Alternative Rendering: Major
                                                        -- HAZMAT fire
   major-hazardous-materials-release          (3103),   -- Alternative Rendering: Major
                                                        -- HAZMAT release
   -- Cancel Types
   disaster-cleared                           (3199),
   -- Disturbances
   assault                                    (3329),   -- This index is not to be used
                                                        -- as a default value for this
                                                        -- category
   crime                                      (3330),
   robbery                                    (3331),
   fare-dispute                               (3332),
   shooting                                   (3333),
   gunfire-on-roadway                         (3334),
   suicide                                    (3335),
   fight                                      (3336),   -- Involves a few  persons and is
                                                        -- localized (alt: brawl)
   gang-fight                                 (3337),   -- Multi-party event occurring
                                                        -- which may involve weapons
   person-harassment                          (3338),   -- "person" may be rendered as
                                                        -- "passenger" if used in a
                                                        -- controlled environment such as
                                                        -- transit
   person-injured                             (3339),
   sick-customer                              (3363),
   unruly-passenger                           (3340),
   person-intoxicated                         (3341),
   crowd-control-problem                      (3342),
   demonstration                              (3343),
   march                                      (3344),
   public-disturbance                         (3345),
   riot                                       (3346),
   civil-unrest                               (3347),
   civil-emergency                            (3348),
   strike                                     (3349),
   public-transit-strike                      (3350),   -- Hint: Strike affecting
                                                        -- services
   stampede                                   (3351),
   teargas-used                               (3352),
   security-alert                             (3353),   -- Heightened security procedures
                                                        -- in effect
   security-incident                          (3354),
   checkpoint                                 (3355),
   bomb-alert                                 (3356),
   terrorist-incident                         (3357),
   high-velocity-shell-fire                   (3358),   -- Hint: Used as a part of
                                                        -- avalanche control
   explosives-in-use                          (3359),
   air-raid                                   (3360),
   weapons-of-mass-destruction-threat         (3361),
   military-operations                        (3362),   -- (war)
   -- Cancel Types
   security-problem-cleared                   (3454),
   traffic-disturbance-cleared                (3455),
   -- Sporting Events
   sports-event                               (3585),
   game                                       (3586),
   tournament                                 (3587),
   track-and-field-event                      (3588),
   baseball-game                              (3589),
   basketball-game                            (3590),
   boxing-match                               (3591),
   football-game                              (3592),
   soccer-game                                (3593),
   golf-tournament                            (3594),
   hockey-game                                (3595),
   tennis-tournament                          (3596),
   wrestling-match                            (3597),
   road-race                                  (3598),   -- Hint: used for motorcycle
                                                        -- races as well
   automobile-race                            (3599),
   bicycle-race                               (3600),
   race-event                                 (3601),
   marathon                                   (3602),
   horse-show                                 (3603),
   rodeo                                      (3604),
   water-sports-event                         (3605),
   winter-sports-event                        (3606),
   skating-event                              (3607),
   dog-sled-race                              (3608),
   -- Cancel Types
   sporting-event-ended                       (3711),
   -- Special Events
   major-event                                (3841),
   airshow                                    (3842),
   hot-air-ballooning                         (3843),
   concert                                    (3844),
   state-occasion                             (3845),
   vIP-visit                                  (3846),
   show                                       (3847),
   festival                                   (3848),   -- Used for farmers' markets as
                                                        -- well
   exhibition                                 (3849),
   performing-arts                            (3850),
   outdoor-market                             (3851),   -- Used for farmers' markets as
                                                        -- well
   fair                                       (3852),
   carnival                                   (3853),
   fireworks-display                          (3854),
   trade-expo                                 (3855),
   movie-filming                              (3856),
   presidential-visit                         (3857),
   parade                                     (3858),
   procession                                 (3859),
   funeral-procession                         (3860),
   crowd                                      (3861),
   holiday-traffic-crowds                     (3862),
   -- Cancel Types
   event-ended                                (3967),
   -- Parking Information
   normal-parking-restrictions-lifted         (4097),   -- Hint: used when a PARKING
                                                        -- restriction is lifted
                                                        -- (overnight parking allowed
                                                        -- during event)  Not to be used
                                                        -- as a default for this category
   parking-meter-restrictions-lifted          (4098),   -- Hint: used when a METER
                                                        -- restriction is lifted (metered
                                                        -- parking free during event)
   special-parking-restrictions-in-force      (4099),
   full-parking-lot                           (4100),
   full-parking-garage                        (4101),
   all-parking-lots-full                      (4102),
   no-parking-spaces-available                (4103),
   only-a-few-spaces-available                (4104),
   spaces-available                           (4105),   -- Typically preceded by a #
                                                        -- value
   no-parking                                 (4106),   -- Typically followed by
                                                        -- restriction data
   parking-on-one-side-of-street-only         (4107),
   parking-on-both-sides-of-street            (4108),
   parallel-parking-only                      (4109),
   parking-meters-not-available               (4110),
   use-of-parking-meters-restricted           (4111),
   event-parking                              (4112),
   handicapped-parking                        (4113),
   long-term-parking                          (4114),
   overnight-parking                          (4115),
   short-term-parking                         (4116),
   parking-by-permit-only                     (4117),
   emergency-parking-only                     (4118),
   emergency-stopping-only                    (4119),
   parking                                    (4120),   -- Typically followed by
                                                        -- restriction data
   stopping                                   (4121),   -- Typically followed by
                                                        -- restriction data
   standing                                   (4122),   -- Typically followed by
                                                        -- restriction data
   tow-away-zone                              (4123),
   school-zone                                (4124),   -- Treat as Speed Limit,
                                                        -- with details to follow
   speed-zone                                 (4125),   -- Treat as Speed Limit,
                                                        -- with details to follow
   loading-zone                               (4126),   -- Typically followed by
                                                        -- restriction data
   state-law                                  (4127),
   van-accessible                             (4128),
   -- Cancel Types
   special-parking-restrictions-lifted        (4222),
   no-parking-information-available           (4223),
   -- Information System
   information-available-on-radio             (4353),   -- Not to be used as a default
                                                        -- for this category D12-1
   information-available-on-TV                (4354),
   call-to-get-information                    (4355),
   information-available-via-Internet         (4356),
   test-message                               (4357),   -- Not to be displayed on
                                                        -- consumer devices if possible
   no-information-available                   (4358),   -- Typically combined with "on
                                                        -- xxx service" where xxx is a
                                                        -- type of service (bus, rail,
                                                        -- etc.)
   null-description                           (4359),   -- (but with event location or
                                                        -- other information provided in
                                                        -- the message)
   police-assistance                          (4361),
   police-monitor-CB                          (4362),   -- D12-3
   emergency-notification                     (4363),
   in-emergency-dial-911                      (4364),   -- D12-14
   travel-Info-call-511                       (4365),   -- D12-5
   car-pool-information                       (4366),   -- D12-2
   information-service-resumed                (4478),
   -- Cancel Types
   information-service-is-being-suspended     (4360),
   message-canceled                           (4479),   -- Not Recommended for use
   -- Weather Conditions
   -- General Weather
   overcast                                   (4609),   -- This index is not to be used
                                                        -- as a default value for this
                                                        -- category
   cloudy                                     (4610),
   mostly-cloudy                              (4611),
   partly-cloudy                              (4612),
   partly-sunny                               (4613),
   mostly-sunny                               (4614),
   sunny                                      (4615),
   fair-skies                                 (4616),
   clear-skies                                (4617),
   mostly-clear                               (4618),
   mostly-dry                                 (4619),
   dry                                        (4620),
   uV-index-very-high                         (4621),
   uV-index-high                              (4622),
   uV-index-moderate                          (4623),
   uV-index-low                               (4624),
   uV-index-very-low                          (4625),
   barometric-pressure                        (4626),   -- Typically followed by a number
                                                        -- and value
   ozone-alert                                (4627),
   -- Lighting Types
   lighting-unknown                           (4628),
   artificial-exterior-light                  (4629),
   artificial-interior-light                  (4630),
   darkness                                   (4631),   -- Also used when not lighted
   dusk                                       (4632),
   dawn                                       (4633),
   moonlight                                  (4634),
   daylight                                   (4635),
   -- Cancel Types
   weather-forecast-withdrawn                 (4735),
   -- Precipitation
   severe-weather                             (4865),
   blizzard                                   (4866),
   heavy-snow                                 (4867),
   snow                                       (4868),
   light-snow                                 (4869),
   snow-showers                               (4870),
   winter-storm                               (4871),
   ice-glaze                                  (4872),
   heavy-frost                                (4873),
   frost                                      (4874),
   ice-storm                                  (4875),
   sleet                                      (4876),
   rain-and-snow-mixed                        (4877),
   rain-changing-to-snow                      (4878),
   damaging-hail                              (4879),
   hail                                       (4880),
   thunderstorms                              (4881),
   thundershowers                             (4882),
   extremely-heavy-downpour                   (4883),
   heavy-rain                                 (4884),
   rain                                       (4885),
   light-rain                                 (4886),
   drizzle                                    (4887),
   showers                                    (4888),
   dew                                        (4889),
   -- Cancel Types
   precipitation-cleared                      (4991),
   -- Winds
   tornado                                    (5121),   -- Note that this can be combined
                                                        -- with "alert" "warning" etc.
                                                        -- This index is not to be used
                                                        -- as a default value for this
                                                        -- category
   hurricane                                  (5122),
   hurricane-force-winds                      (5123),
   tropical-storm                             (5124),
   gale-force-winds                           (5125),
   storm-force-winds                          (5126),
   strong-winds                               (5127),
   moderate-winds                             (5128),
   light-winds                                (5129),
   calm                                       (5130),
   gusty-winds                                (5131),
   crosswinds                                 (5132),
   windy                                      (5133),
   -- Cancel Types
   strong-winds-have-eased                    (5246),
   strong-wind-forecast-withdrawn             (5247),
   -- Visibility & Air Quality
   -- Visibility
   dense-fog                                  (5377),   -- This index is not to be used
                                                        -- as a default value for this
                                                        -- category
   fog                                        (5378),
   patchy-fog                                 (5379),
   freezing-fog                               (5380),
   ice-fog                                    (5405),   -- Different than freezing fog,
                                                        -- ice fog occurs well below
                                                        -- freezing temps and is quite
                                                        -- common in the Fairbanks area.
   mist                                       (5381),
   haze                                       (5382),
   visibility-reduced                         (5383),
   visibility-blocked                         (5404),   -- Used when signs, trees, etc.,
                                                        -- block the view
   white-out                                  (5384),   -- Alternative Rendering: Snow
                                                        -- glare
   blowing-snow                               (5385),
   smoke-hazard                               (5386),
   spray-hazard                               (5387),
   low-sun-glare                              (5388),   -- Do not use for snow glare
   snow-glare                                 (5389),
   blowing-dust                               (5390),
   blowing-sand                               (5391),   -- Hint: dune accumulations
   dust-storms                                (5392),
   sandstorms                                 (5393),
   -- Air Quality
   air-quality-good                           (5394),
   air-quality-fair                           (5395),
   air-quality-poor                           (5396),
   air-quality-very-poor                      (5397),
   severe-exhaust-pollution                   (5398),
   smog-alert                                 (5399),
   pollen-count-high                          (5400),
   pollen-count-medium                        (5401),
   pollen-count-low                           (5402),
   swarms-of-insects                          (5403),
   -- Cancel Types
   fog-clearing                               (5499),
   visibility-improved                        (5500),
   fog-forecast-withdrawn                     (5501),
   pollution-alert-ended                      (5502),
   air-quality-improved                       (5503),
   -- Temperature
   maximum-temperature                        (5633),   -- This index is not to be used
                                                        -- as a default value for this
                                                        -- category
   temperature                                (5634),   -- Typically followed by a number
                                                        -- value and a unit value
   minimum-temperature                        (5635),
   current-temperature                        (5636),
   heat-index                                 (5637),
   extreme-heat                               (5638),
   hot                                        (5639),
   hotter                                     (5640),
   heat                                       (5641),
   warmer                                     (5642),
   warm                                       (5643),
   mild                                       (5644),
   cool                                       (5645),
   cooler                                     (5646),
   cold                                       (5647),
   colder                                     (5648),
   very-cold                                  (5649),
   extreme-cold                               (5650),
   wind-chill                                 (5651),
   dewpoint                                   (5652),
   relative-humidity                          (5653),
   -- Cancel Types
   temperatures-close-to-the-seasonal-norm    (5758),
   less-extreme-temperatures                  (5759),
   -- Pavement Conditions
   -- General
   impassable                                 (5889),
   almost-impassable                          (5890),
   passable-with-care                         (5891),
   passable                                   (5892),
   surface-water-hazard                       (5893),
   danger-of-hydroplaning                     (5894),
   wet-pavement                               (5895),
   treated-pavement                           (5896),   -- Alternative Rendering:
                                                        -- chemical wet
   slippery                                   (5897),
   low-ground-clearance                       (5938),   -- Use for W12-2 types
   at-grade-level-crossing                    (5937),
   -- On Roadway items
   mud-on-roadway                             (5898),
   leaves-on-roadway                          (5899),
   loose-sand-on-roadway                      (5900),
   loose-gravel                               (5901),
   fuel-on-roadway                            (5902),
   oil-on-roadway                             (5903),
   road-surface-in-poor-condition             (5904),
   melting-tar                                (5905),
   uneven-lanes                               (5935),
   rough-road                                 (5931),
   rough-crossing                             (5936),   -- Typically used with grade
                                                        -- crossings at rails
   -- Ice & Snow
   ice                                        (5906),
   icy-patches                                (5907),
   black-ice                                  (5908),
   ice-pellets-on-roadway                     (5909),
   ice-build-up                               (5910),
   freezing-rain                              (5911),
   wet-and-icy-roads                          (5912),
   slush                                      (5914),
   melting-snow                               (5913),
   frozen-slush                               (5915),
   snow-on-roadway                            (5916),
   packed-snow                                (5917),
   packed-snow-patches                        (5918),
   plowed-snow                                (5919),
   wet-snow                                   (5920),
   fresh-snow                                 (5921),
   powder-snow                                (5922),
   granular-snow                              (5923),
   frozen-snow                                (5924),
   crusted-snow                               (5925),
   deep-snow                                  (5926),
   snow-drifts                                (5927),
   drifting-snow                              (5928),
   expected-snow-accumulation                 (5929),
   current-snow-accumulation                  (5930),
   -- Road Surface
   sand                                       (5932),   -- Can use for W7-4d
   gravel                                     (5933),   -- Can use for W7-4e
   paved                                      (5934),   -- Can use for W7-4f
   -- Cancel Types
   dry-pavement                               (6011),
   snow-cleared                               (6012),
   pavement-conditions-improved               (6013),
   skid-hazard-reduced                        (6014),
   pavement-conditions-cleared                (6015),
   -- Winter Driving Restrictions and Recommendations
   winter-equipment-recommended               (6145),
   winter-equipment-required                  (6146),
   snow-chains-recommended                    (6147),
   snow-chains-required                       (6148),
   snow-chains-prohibited                     (6149),
   studded-tires-prohibited                   (6150),
   snow-tires-recommended                     (6151),
   snow-tires-required                        (6152),
   four-wheel-drive-recommended               (6153),
   four-wheel-drive-required                  (6154),
   snow-tires-or-chains-recommended           (6155),
   snow-tires-or-chains-required              (6156),
   -- Cancel Types
   winter-driving-requirements-lifted         (6271),   -- In early editions this was
                                                        -- incorrectly listed as code
                                                        -- 6157
   -- Winter Driving Index
   driving-conditions-good                    (6401),
   driving-conditions-fair                    (6402),
   difficult-driving-conditions               (6403),
   very-difficult-driving-conditions          (6404),
   hazardous-driving-conditions               (6405),
   extremely-hazardous-driving-conditions     (6406),
   -- Suggestion Advice
   why-not-ride-share                         (6657),
   is-this-your-no-ride-day                   (6658),
   why-not-use-transit                        (6659),
   why-not-park-and-ride                      (6660),
   why-not-try-paratransit                    (6661),
   why-not-travel-by-rail                     (6662),
   why-not-use-the-subway                     (6663),
   why-not-try-rapid-transit                  (6664),
   why-not-travel-by-bus                      (6665),
   your-parking-ticket-covers-the-return-ride (6666),
   avoid-the-rush-hour                        (6667),
   do-not-allow-unnecessary-gaps              (6668),
   follow-the-vehicle-in-front-smoothly       (6669),
   do-not-slow-down-unnecessarily             (6670),
   watch-for-muggers                          (6671),
   watch-for-pickpockets                      (6672),
   watch-for-thieves                          (6673),
   sorry-for-any-delay                        (6674),
   thank-you-for-your-understanding           (6675),
   we-appreciate-your-patience                (6676),
   we-are-grateful-for-your-cooperation       (6677),
   share-the-road                             (6678),
   -- Warning Advice
   risk                                       (6913),   -- Conditions are more likely
                                                        -- than "normal"
   watch                                      (6914),   -- Conditions are favorable for
                                                        -- an event to occur
   warning                                    (6915),   -- An event has occurred but is
                                                        -- not (yet) near
   alert                                      (6916),   -- An event has occurred and it
                                                        -- is near
   danger                                     (6917),
   danger-of-explosion                        (6918),
   danger-of-fire                             (6919),
   extra-police-patrols-in-operation          (6920),
   look-out-for-vehicles-stopped-under-bridges (6921),
   increased-risk-of-accident                 (6922),
   rescue-and-recovery-work-in-progress-at-sceneREMOVED (6923),   -- No long used, see item 2825
   police-at-scene                            (6924),
   emergency-vehicles-at-scene                (6925),
   traffic-being-directed-around-accident-area (6926),
   police-directing-traffic                   (6927),
   rescue-workers-directing-traffic           (6928),
   repairs-in-progress                        (6929),
   pilot-car-in-operation                     (6930),
   look-out-for-flagger                       (6931),   -- Alternative Rendering: look
                                                        -- out for flagman
   look-out-for-workers                       (6952),   -- Alternative Rendering:
                                                        -- workers
   police-checks-in-operation                 (6932),   -- Hint: all types of checks
   truck-check-point                          (6937),
   lockdown                                   (6935),
   security-check-point                       (6936),
   single-occupancy-vehicle-check-point       (6938),
   mandatory-speed-limit-in-force             (6933),
   speed-limit-in-force-for-heavy-vehicles    (6934),
   behind-you                                 (6950),
   ride-with-traffic                          (6953),
   prepare-to-evacuate-area                   (6954),
   avoid                                      (6955),
   -- MUTCD Signs
   look                                       (6939),
   photo-enforced                             (6940),
   traffic-signs                              (6951),
   traffic-laws                               (6941),
   use-low-gear                               (6942),
   bridge-ices-before-road                    (6943),
   speed-checked-by-radar                     (6944),
   speed-checked-by-aircraft                  (6945),
   fines                                      (6946),
   fines-higher                               (6947),
   fines-doubled                              (6948),
   fines-tripled                              (6949),
   -- Cancel Types
   evacuation-canceled                        (7033),
   warning-canceled                           (7034),   -- Canceling a warning may
                                                        -- "revert" to a watch
   watch-canceled                             (7035),
   alert-canceled                             (7036),   -- Canceling an alert may
                                                        -- "revert" to a warning
   ended                                      (7037),   -- Hint: used for many sporting/
                                                        -- special events
   cleared                                    (7038),
   canceled                                   (7039),
   -- Instructions (Recommendations)
   drive-carefully                            (7169),
   drive-with-extreme-caution                 (7170),
   approach-with-care                         (7171),
   keep-your-distance                         (7172),
   increase-normal-following-distance         (7173),
   test-your-brakes                           (7174),
   cross-intersection-with-care               (7175),
   pass-with-care                             (7176),   -- Use as MUTCD sign
   pass                                       (7200),   -- Used for passing action,
                                                        -- as in do not pass
   use-low-beam-headlights                    (7177),
   use-fog-lights                             (7178),
   use-hazard-warning-lights                  (7179),   -- Alternative Rendering: use
                                                        -- blinkers
   do-not-leave-your-vehicle                  (7180),
   leave-your-vehicle-and-proceed-to-next-safe-place (7181),
   turn-off-engine                            (7182),   -- Alternative Rendering: switch
                                                        -- off engine
   close-all-windows-turn-off-heater-air-conditioner-and-vents (7183),
   turn-off-air-conditioner-to-prevent-engine-overheating (7184),
   turn-off-mobile-phones-and-two-way-radios  (7185),   -- Alternative Rendering: switch
                                                        -- off mobile phones and two way
                                                        -- radios
   prepare-to-stop                            (7186),
   be-prepared-to-stop                        (7201),
   stop-at-next-rest-area                     (7187),
   stop-at-next-safe-place                    (7188),
   only-travel-if-absolutely-necessary        (7189),
   drive-to-another-service-area              (7190),
   use-through-traffic-lanes                  (7191),
   use-local-traffic-lanes                    (7192),
   use-left-hand-parallel-roadway             (7193),
   use-right-hand-parallel-roadway            (7194),
   use-heavy-vehicle-lane                     (7195),   -- Alternative Rendering: use
                                                        -- truck lanes
   observe-recommended-speed                  (7196),
   signals-sequenced-for-speed                (7202),   -- Typically followed by speed
   maintain-top-safe-speed                    (7203),
   facing-traffic                             (7197),
   push-button                                (7198),
   to-cross-street                            (7199),
   evacuate-area-voluntarily                  (7204),
   shelter-in-place                           (7205),
   -- Instructions (Mandatory)
   keep-to-the-right                          (7425),
   keep-to-the-left                           (7426),
   use-right-lane                             (7427),
   use-left-lane                              (7428),
   stay-in-lane                               (7450),
   merge                                      (7451),   -- Typically followed by
                                                        -- direction left/right Used for
                                                        -- W4-1R and W4-1L
   heavy-vehicles-use-right-lane              (7429),
   heavy-vehicles-use-left-lane               (7430),
   observe-signals                            (7431),
   observe-signs                              (7432),
   no-passing                                 (7433),   -- Used for MUTCD signs
   no-smoking                                 (7434),
   no-open-flames                             (7435),
   use-shoulder-as-lane                       (7436),
   do-not-drive-on-the-shoulder               (7437),
   allow-emergency-vehicles-to-pass           (7438),
   clear-a-lane-for-emergency-vehicles        (7439),
   pull-over-to-the-edge-of-the-roadway       (7440),
   wait-for-escort-vehicle                    (7441),
   in-emergency-wait-for-police-patrol        (7442),
   reduce-your-speed                          (7443),
   observe-speed-limits                       (7444),
   check-point                                (7445),
   entry-requirements                         (7446),
   insurance-requirements                     (7447),
   firearms-requirements                      (7448),
   pet-requirements                           (7449),
   slower-traffic-keep-right                  (7452),
   keep-off                                   (7453),   -- Typically followed by
                                                        -- object
   evacuate-area-immediately                  (7454),
   -- Cancel Types
   shoulder-travel-no-longer-allowed          (7547),
   -- Qualifiers
   -- Locations
   above                                      (7681),   -- Not to be used as the default
                                                        -- for this category
   below                                      (7682),
   in                                         (7683),
   around                                     (7684),
   after                                      (7685),
   before                                     (7686),
   at                                         (7687),   -- Hint: used in conjunction with
                                                        -- generic locations
   on                                         (7688),   -- Hint: used in conjunction with
                                                        -- "roadway" or other terms for
                                                        -- both places (on-shoulder) and
                                                        -- events (on-green)
   near                                       (7689),   -- Hint: used with generic
                                                        -- locations and lanes
   from-the                                   (7690),
   terminal                                   (7691),
   -- Weather Related
   falling-slowly                             (7692),
   falling                                    (7693),
   falling-quickly                            (7694),
   rising-slowly                              (7695),
   rising                                     (7696),
   rising-quickly                             (7697),
   steady                                     (7698),
   likely                                     (7699),
   changing-to                                (7700),
   mostly                                     (7701),
   partly                                     (7702),
   minus                                      (7703),
   weather-ended                              (7704),
   expected                                   (7705),
   low                                        (7706),   -- Typically used in
                                                        -- temperatures. See also "upper"
   mid                                        (7707),
   high                                       (7708),
   upper                                      (7709),   -- Typically used in temperatures or broad regions.
                                                        -- See also "low", "mid", "high", "middle"
   middle                                     (7765),  -- Typically used for broad regions
                                                       -- See also "upper", "lower"
   lower                                      (7764),  -- Typically used for broad regions
                                                       -- See also "upper", "middle"
   unseasonably                               (7710),
   reported                                   (7711),
   -- Instructions
   advice                                     (7712),
   due-to                                     (7713),
   proceed-to                                 (7714),
   transferred-to                             (7715),
   use                                        (7716),
   -- Prepositional Use
   affecting                                  (7717),
   blocking                                   (7718),
   connecting                                 (7719),
   finished                                   (7720),   -- Alt term: finish
   for                                        (7721),
   or                                         (7722),
   -- Other
   and                                        (7723),
   later                                      (7724),
   level                                      (7725),
   shortly                                    (7726),
   soon                                       (7727),
   service                                    (7728),
   graffiti                                   (7733),
   damaged                                    (7729),
   out-of-order                               (7730),   -- See Asset Status items as well
   on-State-right-of-way                      (7732),
   found-property                             (7734),
   vandalism                                  (7731),
   major                                      (7766),
   minor                                      (7767),
   -- MUTCD Sign Usage
   begin-time                                 (7735),   -- Typically followed by a
                                                        -- value entry and a time entry
                                                        -- (AM/PM)
   added                                      (7736),   -- Typically preceded by an
                                                        -- object entry
   end-time                                   (7737),   -- Typically followed by a
                                                        -- value entry and a time entry
                                                        -- (AM/PM)
   no                                         (7738),   -- Typically followed by a
                                                        -- value entry and any day/time
                                                        -- limits
   do-not                                     (7739),   -- Also used for "does not"
   block                                      (7740),   -- Also used for blocks
   except                                     (7741),   -- Typically followed by a
                                                        -- value entry and a day/time
                                                        -- entry
   day                                        (7742),   -- Alt: daytime, daylight
                                                        -- hours
   night                                      (7743),   -- Alt: night time, night
                                                        -- time hours
   any-time                                   (7744),   -- Used also for "allowed"
   has                                        (7745),   -- As in: has green (alt
                                                        -- form: with)
   must                                       (7757),   -- As in: <lane> must <turn>
   may-have                                   (7746),   -- As in: may have green
   may-exceed                                 (7759),   -- As in: may exceed 80 mph
   only                                       (7747),
   lifted                                     (7748),   -- As in gate lifted
   empty                                      (7749),
   turning                                    (7750),   -- Used also for turns or
                                                        -- turn
   u-turn                                     (7751),   -- As in no u-turn allowed
   wait-for                                   (7752),
   when-flashing                              (7753),
   duration                                   (7754),   -- Typically followed by a
                                                        -- value entry and a time entry
                                                        -- (Days/Hours/Min)
   cross                                      (7755),
   when-wet                                   (7756),
   oncoming                                   (7758),   -- Typically followed by
                                                        -- object or vehicle types
   to-request                                 (7760),   -- As in to request X do Y
   exempt                                     (7761),
   skewed                                     (7762),
   when-children-are-present                  (7763),   -- Use for S4-2
   -- Generic Locations
   -- Road Related
   on-bridges                                 (7937),   -- Not to be used as the default
                                                        -- for this category
   in-tunnels                                 (7938),
   entering-or-leaving-tunnels                (7939),
   on-ramps                                   (7940),
   in-road-construction-area                  (7941),
   around-a-curve                             (7942),
   on-curve                                   (8026),
   on-tracks                                  (8009),
   in-street                                  (8025),   -- As in in-street pad
                                                        -- crossing
   shoulder                                   (8027),
   on-minor-roads                             (7943),
   in-the-opposing-lanes                      (7944),
   adjacent-to-roadway                        (7945),
   across-tracks                              (8024),
   on-bend                                    (7946),
   intersection                               (8032),
   entire-intersection                        (7947),
   in-the-median                              (7948),
   moved-to-side-of-road                      (7949),
   moved-to-shoulder                          (7950),
   on-the-roadway                             (7951),   -- Use generic locations and
                                                        -- groups affected to make other
                                                        -- such phrases
   dip                                        (8010),   --
   traffic-circle                             (8011),   -- Used for W2-6 graphic as
                                                        -- well. Alt term: roundabout
   crossover                                  (8028),
   cross-road                                 (8029),   -- Also used for W2-1 Note
                                                        -- that in some uses this is one
                                                        -- word
   side-road                                  (8030),   -- Do not used for W2-2R and
                                                        -- W2-2L
   to                                         (8014),
   by                                         (8015),
   through                                    (8016),
   area-of                                    (8017),   -- Also area
   under                                      (8018),
   over                                       (8019),
   from                                       (8020),
   approaching                                (8021),
   entering-at                                (8022),   -- Alt form: Entrance
   exiting-at                                 (8023),
   -- Terrain & Geography
   in-shaded-areas                            (7952),
   in-low-lying-areas                         (7953),
   in-the-downtown-area                       (7954),
   in-the-inner-city-area                     (7955),
   in-parts                                   (7956),
   in-some-places                             (7957),
   in-the-ditch                               (7958),
   in-the-valley                              (7959),
   on-hill-top                                (7960),
   near-the-foothills                         (7961),
   at-high-altitudes                          (7962),
   near-the-lake                              (7963),
   near-the-shore                             (7964),
   nearby-basin                               (8008),
   over-the-crest-of-a-hill                   (7965),
   other-than-on-the-roadway                  (7966),
   near-the-beach                             (7967),
   near-beach-access-point                    (7968),
   mountain-pass                              (8006),
   lower-level                                (7969),
   upper-level                                (7970),
   coast                                      (8034),
   -- Transit Travel, Air Travel and Places
   airport                                    (7971),
   concourse                                  (7972),
   gate                                       (7973),
   baggage-claim                              (7974),
   customs-point                              (7975),
   reservation-center                         (8007),
   station                                    (7976),
   platform                                   (7977),   -- Alternative Rendering: track
   dock                                       (7978),
   depot                                      (7979),
   ev-charging-point                          (7980),
   information-welcome-point                  (7981),   -- Use for Tourist Information as
                                                        -- well (D9-10)
   at-rest-area                               (7982),
   at-service-area                            (7983),
   at-weigh-station                           (7984),
   roadside-park                              (8033),
   picnic-areas                               (7985),
   rest-area                                  (7986),
   service-stations                           (7987),
   toilets                                    (7988),   -- Note also rest rooms in
                                                        -- structures
   bus-stop                                   (8031),
   park-and-ride-lot                          (8012),   -- Not to be used as a mode
                                                        -- of travel
   -- Direction of Travel
   on-the-right                               (7989),
   on-the-left                                (7990),
   in-the-center                              (7991),
   in-the-opposite-direction                  (7992),
   cross-traffic                              (7993),
   northbound-traffic                         (7994),
   eastbound-traffic                          (7995),
   southbound-traffic                         (7996),
   westbound-traffic                          (7997),
   -- Compass Points
   north                                      (7998),
   south                                      (7999),
   east                                       (8000),
   west                                       (8001),
   northeast                                  (8002),
   northwest                                  (8003),
   southeast                                  (8004),
   southwest                                  (8005),
   -- Lane/Roadway Descriptions
   -- Lanes
   all-roadways                               (8193),   -- Used as the default value
   through-lanes                              (8194),
   left-lane                                  (8195),
   right-lane                                 (8196),
   center-lane                                (8197),
   middle-lanes                               (8198),
   middle-two-lanes                           (8199),
   right-turning-lanes                        (8200),
   left-turning-lanes                         (8201),
   upper-deck-lanes                           (8236),
   lower-deck-lanes                           (8237),
   reversible-lanes                           (8238),
   right-exit-lanes                           (8239),
   left-exit-lanes                            (8240),
   right-merging-lanes                        (8241),
   left-merging-lanes                         (8242),
   -- Ramps
   right-exit-ramp                            (8202),
   right-second-exit-ramp                     (8243),
   right-entrance-ramp                        (8203),
   right-second-entrance-ramp                 (8245),
   left-exit-ramp                             (8204),
   left-second-exit-ramp                      (8244),
   left-entrance-ramp                         (8205),
   left-second-entrance-ramp                  (8246),
   escape-ramp                                (8234),   -- A truck feature on steep
                                                        -- downgrades common in both
                                                        -- Alaska and elsewhere.
   -- Shoulders
   hard-shoulder                              (8206),
   soft-shoulder                              (8207),
   right-shoulder                             (8208),
   left-shoulder                              (8209),
   median                                     (8252),
   sidewalk                                   (8251),
   -- Other
   highways                                   (8235),
   right-hand-parallel-lanes                  (8210),   -- Alternative Rendering:
                                                        -- right-hand frontage road
   left-hand-parallel-lanes                   (8211),   -- Alternative Rendering:
                                                        -- left-hand frontage road
   connecting-lanes                           (8212),
   express-lanes                              (8213),
   local-lanes                                (8214),
   toll-lanes                                 (8215),
   electronic-toll-lanes                      (8216),
   toll-plaza                                 (8217),
   inspection-lane                            (8218),   -- Alternative Rendering: Border
                                                        -- patrol inspection lane
   hOV-lanes                                  (8219),   -- Use when 2+ or 3+ is unknown
                                                        -- and for HOV in general
   bus-lanes                                  (8220),
   carpool-lanes                              (8221),
   truck-lanes                                (8222),
   emergency-lanes                            (8223),
   passing-lanes                              (8224),
   climbing-lanes                             (8225),
   slow-lane                                  (8226),   -- Alternative Rendering:
                                                        -- Crawler lane
   service-road                               (8227),   -- Alternative Rendering:
                                                        -- Frontage Road
   cycle-lane                                 (8228),   -- Use for bicycle lanes of all
                                                        -- types
   tracks                                     (8250),   -- Use for light rail and
                                                        -- transit uses, may have count
                                                        -- of tracks
   -- Bridges, Tunnels
   bridge                                     (8229),
   overpass                                   (8230),
   elevated-lanes                             (8231),
   underpass                                  (8232),
   tunnel                                     (8233),   -- Use for RG-200
   -- Lanes Groups
   all-exit-lanes                             (8247),
   all-entry-lanes                            (8248),
   either-shoulder                            (8249),
   shoulder-work                              (8253),   -- Use for W21-5 as well
   -- Alternate Route
   detour-where-possible                      (8449),
   no-detour-available                        (8450),
   follow-signs                               (8451),
   follow-detour-signs                        (8452),
   follow-special-detour-markers              (8453),
   do-not-follow-detour-signs                 (8454),
   detour-in-operation                        (8455),
   follow-local-detour                        (8456),
   compulsory-detour-in-operation             (8457),
   no-suitable-detour-available               (8458),
   detour-is-no-longer-recommended            (8459),
   local-drivers-are-recommended-to-avoid-the-area (8460),
   trucks-are-recommended-to-avoid-the-area   (8461),
   consider-alternate-route                   (8462),
   consider-alternate-parking                 (8463),
   consider-alternate-destination             (8464),
   consider-alternate-area                    (8465),
   -- Specific Route Types
   snow-route                                 (8466),
   emergency-snow-route                       (8467),
   evacuation-route                           (8468),   -- May be preceded by a
                                                        -- specific type, Used also for
                                                        -- general emergency routes.
   truck-route                                (8469),
   hazardous-materials-route                  (8470),   -- May be used with 'any
                                                        -- time' for allowed, or 'no' for
                                                        -- prohibited, or 'detour'
   detour                                     (8471),
   -- Unit Values
   -- Areas,  Distances  &  Speeds
   square-feet                                (8705),
   square-meters                              (8706),
   acres                                      (8707),
   hectares                                   (8708),
   inches                                     (8709),
   feet                                       (8710),
   mile                                       (8711),   -- Hint: used for offset as in
                                                        -- "at mile 123"  Alternative
                                                        -- Rendering: milepost marker
   miles                                      (8712),   -- Hint: Used for distance, as in
                                                        -- "ending 5 miles"
   nautical-miles                             (8713),
   millimeters                                (8714),
   meters                                     (8715),
   kilometer                                  (8716),   -- Hint: used for offset as in
                                                        -- "at kilometer 123"
   kilometers                                 (8717),
   feet-per-second                            (8718),
   meters-per-second                          (8719),
   mPH                                        (8720),
   kPH                                        (8721),
   knots                                      (8722),
   elevation                                  (8766),   -- Typically followed by
                                                        -- value and units
   -- Times,  Days  &  Dates
   aM                                         (8723),   -- Both a time value and a radio
                                                        -- band value. A number value
                                                        -- may PRECEDE the unit value
                                                        -- used in representing the
                                                        -- frequency of a radio station
   pM                                         (8724),
   holiday                                    (8726),
   seconds                                    (8727),
   minutes                                    (8728),
   hours                                      (8729),
   days                                       (8730),   -- Hint: useful for events
                                                        -- occurring for at least 24
                                                        -- hours
   weeks                                      (8731),
   months                                     (8732),
   other-times                                (8767),   -- Typically used to
                                                        -- represent a "default" allowed
                                                        -- condition
   -- Days of the Week
   nSunday                                    (8758),
   nMonday                                    (8759),
   nTuesday                                   (8760),
   nWednesday                                 (8761),
   nThursday                                  (8762),
   nFriday                                    (8763),
   nSaturday                                  (8764),
   weekdays                                   (8765),   -- Alt text: Mon-Fri
   weekends                                   (8725),   -- In general date/time values
                                                        -- can be better coded in other
                                                        -- ways in most message sets
   -- Temps, Weights, Masses and Measurements
   degrees-Angle                               (8733),   -- Used for latitude, longitude
                                                        -- and bearing measured clockwise
                                                        -- from North
   degrees-Celsius                            (8734),   -- Alternate renderings possible
   degrees-Fahrenheit                         (8735),   -- Alternate renderings possible
   grams                                      (8736),
   kilograms                                  (8737),   -- Also called a metric ton
                                                        -- (1000kg or ~2204 lbs)
   ounces                                     (8738),
   pounds                                     (8739),
   tons                                       (8740),   -- English Units (2000 lbs = 1
                                                        -- ton)
   fluid-ounces                               (8741),
   gallons                                    (8742),
   milliliters                                (8743),
   liters                                     (8744),
   kilograms-per-lane-mile                    (8745),
   tons-per-lane-mile                         (8746),
   -- Misc.
   dollar                                     (8747),   -- Alternative rendering: dollar
                                                        -- symbol  Not to be used as the
                                                        -- default value for this
                                                        -- category
   percent                                    (8748),   -- Alternative rendering: percent
                                                        -- symbol
   grade                                      (8757),   -- Typically preceded by a
                                                        -- percent value entry
   time-delimiter                             (8749),   -- Alternative rendering: "-"
   dollars                                    (8750),   -- Alternative rendering can use
                                                        -- local currency sign
   flight-number                              (8751),   -- A number value may PRECEDE the
                                                        -- unit value in use
   person-people                              (8752),
   response-plan                              (8753),   -- A value may PRECEDE the unit
                                                        -- value in use (involving a
                                                        -- combination of numbers and/
                                                        -- or letters)
   placard-type                               (8754),   -- For hazmat class and division
                                                        -- type designations, a value may
                                                        -- PRECEDE the unit value in use
   placard-number                             (8755),   -- For chemical designations, a
                                                        -- value may PRECEDE the unit
                                                        -- value in use
   fM                                         (8756),   -- A number value may PRECEDE the
                                                        -- unit value in use representing
                                                        -- the frequency of a radio
                                                        -- station
   -- Transit Mode
   travel                                     (8961),   -- Hint: may include all modes
   transit                                    (8962),   -- Hint: may include all public
                                                        -- transit modes
   bus                                        (8963),
   trolleybus                                 (8964),
   rail                                       (8965),
   commuter-rail                              (8966),
   subway                                     (8967),
   rapid-transit                              (8968),
   light-rail                                 (8969),
   streetcar                                  (8970),   -- Alternative Rendering: tram
   dial-a-ride                                (8971),   -- Alternative Rendering: demand
                                                        -- responsive transit
   park-and-ride                              (8972),   -- Not to be used as a place
   shuttle                                    (8973),
   free-shuttle                               (8974),   -- Alternative Rendering: tram
   airport-shuttle                            (8975),
   taxies                                     (8976),
   ferry                                      (8977),
   passenger-ferry                            (8978),
   vehicle-ferry                              (8979),
   aerial-tramway                             (8980),
   automated-guideway                         (8981),   -- Include all types of guideways
   cable-cars                                 (8982),
   monorail                                   (8983),
   air-travel                                 (8984),   -- All modes of air travel
   hitch-hitching                             (8985),
   walk                                       (8986),   -- Alt form: Walking
   -- Vehicle Groups Affected
   all-vehicles                               (9217),
   bicycles                                   (9218),
   motorcycles                                (9219),   -- to include mopeds as well
   cars                                       (9220),   -- (remapped from ERM value of
                                                        -- zero)
   light-vehicles                             (9221),
   cars-and-light-vehicles                    (9222),
   cars-with-trailers                         (9223),
   cars-with-recreational-trailers            (9224),
   vehicles-with-trailers                     (9225),
   heavy-vehicles                             (9226),
   trucks                                     (9227),   -- Use for RG-190
   buses                                      (9228),
   articulated-buses                          (9229),
   school-buses                               (9230),
   vehicles-with-semi-trailers                (9231),
   vehicles-with-double-trailers              (9232),   -- Alternative Rendering:
                                                        -- western doubles
   high-profile-vehicles                      (9233),
   wide-vehicles                              (9234),
   long-vehicles                              (9235),
   hazardous-loads                            (9236),
   exceptional-loads                          (9237),
   abnormal-loads                             (9238),
   convoys                                    (9239),
   maintenance-vehicles                       (9240),
   delivery-vehicles                          (9241),
   vehicles-with-even-numbered-license-plates (9242),
   vehicles-with-odd-numbered-license-plates  (9243),
   vehicles-with-parking-permits              (9244),
   vehicles-with-catalytic-converters         (9245),
   vehicles-without-catalytic-converters      (9246),
   gas-powered-vehicles                       (9247),
   diesel-powered-vehicles                    (9248),
   lPG-vehicles                               (9249),
   military-convoys                           (9250),
   military-vehicles                          (9251),
   electric-powered-vehicles                  (9252),
   hybrid-powered-vehicles                    (9253),
   inherently-low-emission-vehicles            (9254),
   commercial-vehicles                        (9255),
   runaway-vehicles                           (9256),
   vehicles-with-lugs                         (9257),
   motor-driven-cycles                        (9258),
   recreational-vehicles                      (9259),   -- Use for RVs
   non-motorized-vehicles                     (9260),
   traffic                                    (9261),   -- Refers to all types of
                                                        -- motor traffic, all groups
   -- Traveler Group Affected
   through-traffic                            (9473),
   holiday-traffic                            (9474),
   residents                                  (9475),
   visitors                                   (9476),
   long-distance-traffic                      (9477),
   local-traffic                              (9478),
   regional-traffic                           (9479),
   arrivals                                   (9480),
   departures                                 (9481),
   airline-travelers                          (9482),
   commuter-airline-travelers                 (9483),
   domestic-airline-travelers                 (9484),
   international-airline-travelers            (9485),
   pedestrians                                (9486),
   bicyclists                                 (9487),   -- Hint: may be used as a
                                                        -- traveler restriction, as in
                                                        -- "bicycles prohibited on
                                                        -- subways during rush hour" or
                                                        -- "road closed to bicyclists"
   -- Responder Group Affected
   emergency-vehicle-units                    (9729),   -- Default phrase, to be used
                                                        -- when one of the below does not
                                                        -- fit better
   federal-law-enforcement-units              (9730),
   state-police-units                         (9731),
   county-police-units                        (9732),   -- Hint: also sheriff response
                                                        -- units
   local-police-units                         (9733),
   ambulance-units                            (9734),
   rescue-units                               (9735),
   fire-units                                 (9736),
   hAZMAT-units                               (9737),   -- Any vehicle assigned to HAZMAT
                                                        -- duties
   light-tow-unit                             (9738),
   heavy-tow-unit                             (9739),
   private-tow-units                          (9743),   -- For 3rd Party tow trucks
   freeway-service-patrols                    (9740),
   transportation-response-units              (9741),
   private-contractor-response-units          (9742),
   -- Incident Response Equipment
   ground-fire-suppression                    (9985),
   heavy-ground-equipment                     (9986),
   aircraft                                   (9988),
   marine-equipment                           (9989),
   support-equipment                          (9990),
   medical-rescue-unit                        (9991),
   other                                      (9993),   -- Depreciated by fire standards,
                                                        -- do not use
   ground-fire-suppression-other              (9994),
   engine                                     (9995),
   truck-or-aerial                            (9996),
   quint                                      (9997),   -- A five-function type of fire
                                                        -- apparatus. The units in the
                                                        -- movie Backdraft were quints
   tanker-pumper-combination                  (9998),
   brush-truck                                (10000),
   aircraft-rescue-firefighting               (10001),
   heavy-ground-equipment-other               (10004),
   dozer-or-plow                              (10005),
   tractor                                    (10006),
   tanker-or-tender                           (10008),
   aircraft-other                             (10024),
   aircraft-fixed-wing-tanker                 (10025),
   helitanker                                 (10026),
   helicopter                                 (10027),
   marine-equipment-other                     (10034),
   fire-boat-with-pump                        (10035),
   boat-no-pump                               (10036),
   support-apparatus-other                    (10044),
   breathing-apparatus-support                (10045),
   light-and-air-unit                         (10046),
   medical-rescue-unit-other                  (10054),
   rescue-unit                                (10055),
   urban-search-rescue-unit                   (10056),
   high-angle-rescue                          (10057),
   crash-fire-rescue                          (10058),
   bLS-unit                                   (10059),
   aLS-unit                                   (10060),
   mobile-command-post                        (10075),  -- Deprecated, do not use
   chief-officer-car                          (10076),
   hAZMAT-unit                                (10077),
   type-i-hand-crew                           (10078),
   type-ii-hand-crew                          (10079),
   privately-owned-vehicle                    (10083),  -- (Often found in volunteer fire
                                                        -- teams)
   other-apparatus-resource                   (10084),  -- (Remapped from fire code zero)
   ambulance                                  (10085),
   bomb-squad-van                             (10086),
   combine-harvester                          (10087),
   construction-vehicle                       (10088),
   farm-tractor                               (10089),
   grass-cutting-machines                     (10090),
   hAZMAT-containment-tow                     (10091),
   heavy-tow                                  (10092),
   light-tow                                  (10094),
   flatbed-tow                                (10114),
   hedge-cutting-machines                     (10093),
   mobile-crane                               (10095),
   refuse-collection-vehicle                  (10096),
   resurfacing-vehicle                        (10097),
   road-sweeper                               (10098),
   roadside-litter-collection-crews           (10099),
   survey-crews                               (10115),
   salvage-vehicle                            (10100),
   sand-truck                                 (10101),
   snowplow                                   (10102),
   steam-roller                               (10103),
   swat-team-van                              (10104),
   track-laying-vehicle                       (10105),
   unknown-vehicle                            (10106),
   white-lining-vehicle                       (10107),  -- Consider using Roadwork "road
                                                        -- marking operations" unless the
                                                        -- objective is to refer to the
                                                        -- specific vehicle of this type.
                                                        -- Alternative Rendering: line
                                                        -- painting vehicle
   dump-truck                                 (10108),
   supervisor-vehicle                         (10109),
   snow-blower                                (10110),
   rotary-snow-blower                         (10111),
   road-grader                                (10112),  -- Alternative term: motor grader
   steam-truck                                (10113),  -- A special truck that thaws
                                                        -- culverts and storm drains
   -- Asset Status
   unknown-status                             (10240),  -- Used when status is not known
   ready-for-use                              (10241),
   working-normally                           (10242),
   working-autonomously                       (10243),
   working-incorrectly                        (10244),
   not-working                                (10245),
   normal-maintenance                         (10246),
   in-route-to-use                            (10247),
   returning-from-use                         (10248),
   out-of-service                             (10249),
   off-duty                                   (10250),
   on-patrol                                  (10251),
   on-call                                    (10252),
   on-break                                   (10253),
   mandatory-time-off                         (10254),
   low-on-fuel                                (10255),
   low-on-water                               (10256),
   low-charge                                 (10257),
   missing                                    (10258),  -- Use "sign down" in device
                                                        -- status if an object is damaged
                                                        -- (or use "damaged") and could
                                                        -- be returned to service, use
                                                        -- "missing" only if an object is
                                                        -- in fact missing
   -- Roadside Assets
   -- Inanimate Objects
   none                                       (10496),  -- Implies free text follows
   light-pole                                 (10497),
   utility-pole                              (10498),
   gantry-way                                 (10499),
   sign-support                               (10500),  -- All forms of signage
   signal-pole                                (10501),
   signage-public                             (10502),
   signage-private                            (10503),
   overhead-sign                              (10568),
   ground-sign                                (10569),
   cones                                      (10504),  -- Typical std height cones as
                                                        -- per MUTCD
   cones-post-type                            (10505),  -- Also called channelizer cones
                                                        -- or delineator posts
   cones-glue-post                            (10506),  -- For all glue-down types
   cones-other                                (10507),  -- Specialty types or misc.
                                                        -- smaller cones
   barriers                                   (10508),
   barrier-Aframe                             (10509),  -- Sizes larger than 1.5 meters
                                                        -- in length
   barriers-heavy-duty                        (10510),  -- All types requiring equipment
                                                        -- to place
   barricade-type-III                         (10511),  -- All collapsible Type III
                                                        -- Barricades
   barricade-small                            (10512),  -- Type I and all small A frame
                                                        -- types, also so-called "mini"
                                                        -- or "narrows" types
   solid-barrier                              (10565),
   moveable-barrier                           (10566),
   barricade-lights                           (10513),  -- Std 7" light as per ITE stds
   beacon                                     (10514),  -- All types of strobe and
                                                        -- rotating lights
   t-stand                                    (10515),
   a-stand                                    (10516),
   drums                                      (10517),  -- Common drums and barrel types
   sand-barrel                                (10567),
   impact-attenuator                          (10518),  -- Water-filled and other
                                                        -- crushable types
   barricade-tape                             (10519),  -- Lettering type (legend) to be
                                                        -- conveyed elsewhere
   safety-fence                               (10520),
   temp-pavement-markings                     (10521),  -- All forms of temp markings
   speed-bumps                                (10522),  -- Use also for speed humps
   temp-curbs                                 (10523),
   parking-blocks                             (10524),
   signboard-fixed                            (10525),
   signboard-portable                         (10526),
   stripe                                     (10572),
   island                                     (10573),  -- Used for raised islands
                                                        -- in median
   -- Controllable or Active Objects
   har                                        (10527),  -- Transmission type not known
   har-AM                                     (10528),
   har-FM                                     (10529),
   har-DSRC                                   (10530),
   traffic-light                              (10531),  -- Also used for signalized
                                                        -- intersections
   lane-control-signal                        (10532),
   traffic-detector                           (10533),
   vehicle-detector                           (10534),
   system-alarm                               (10535),
   arrow-board                                (10536),
   fixed-VMS                                  (10537),
   mobile-VMS                                 (10538),
   ramp-control                               (10539),
   gate-control                               (10540),  -- Other than rail types
   temporary-traffic-light                    (10541),
   over-height-warning-system                 (10542),
   over-weight-warning-system                 (10543),
   emergency-telephones                       (10544),
   railroad-crossing-equipment                (10545),
   tunnel-ventilation                         (10546),  -- Use also for fans
   ccTV                                       (10547),
   environmental-sensor                       (10548),
   emergency-signal                           (10570),
   countdown-pedestrian-sign                  (10571),
   -- Items Used by Rail and Transit
   switch                                     (10549),  -- In the context of a railroad
                                                        -- device
   signal                                     (10550),  -- In the context of a railroad
                                                        -- device
   third-rail                                 (10551),
   overhead-power                             (10552),  -- Specifically the power feed
                                                        -- line for a vehicle, do not use
                                                        -- for general power lines
   concrete-tie                               (10553),
   wooden-tie                                 (10554),
   manhole-cover                              (10559),
   -- Misc. Items
   culvert                                    (10560),
   escalator                                  (10555),
   elevator                                   (10556),
   snow-poles                                 (10561),  -- A tall pole and overhanging
                                                        -- arm (like a luminaire) with
                                                        -- reflective markers to help
                                                        -- indicate roadway in mountain
                                                        -- passes during whiteout
                                                        -- conditions
   track                                      (10557),
   guide-poles                                (10562),  -- Poles along road to indicate
                                                        -- guard rail in deep snow
   drawbridge                                 (10558),
   expansion-joint                            (10563),
   shifted-plate                              (10564),
   -- Transit Operations
   unknown-transit-problem                    (10753),
   sleeping-customer                          (10754),
   assault-on-passenger                       (10755),
   assault-on-employee                        (10756),
   broken-seat                                (10757),
   bus-alarm                                  (10758),
   crime-or-drug-deal                         (10759),
   eating-on-board                            (10760),
   equipment-problem-with-air-conditioning    (10761),
   equipment-problem-with-air-system          (10762),
   equipment-problem-with-brakes              (10763),
   equipment-problem-with-chassis-or-suspension (10764),
   equipment-problem-with-cooling-system      (10765),
   equipment-problem-with-doors               (10766),
   equipment-problem-with-electrical          (10767),
   equipment-problem-with-engine              (10768),
   equipment-problem-with-exterior-or-body    (10769),
   equipment-problem-with-fare-collection     (10770),
   equipment-problem-with-fuel-or-exhaust     (10771),
   equipment-problem-with-horn                (10772),
   equipment-problem-with-interior            (10773),
   equipment-problem-with-liftkneeling        (10774),
   equipment-problem-with-lights              (10775),
   equipment-problem-with-lubrication         (10776),
   equipment-problem-with-radio-or-communication (10777),
   equipment-problem-with-signs               (10778),
   equipment-problem-with-steering            (10779),
   equipment-problem-with-tires               (10780),
   equipment-problem-with-transmission        (10781),
   equipment-problem-with-unknown-alarm       (10782),
   equipment-problem-with-wipers              (10783),
   fare-dispute-expired-pass                  (10784),
   fare-dispute-expired-transfer              (10785),
   fare-dispute-expired-upgrade               (10786),
   fare-dispute-other                         (10787),
   fare-dispute-refuses-to-pay                (10788),
   lift-passenger-cycle-completed             (10789),
   lift-passenger-ready-to-alight             (10790),
   lift-passenger-ready-to-board              (10791),
   lost-article                               (10792),
   objects-thrown                             (10793),
   passenger-accident-alighting               (10794),
   passenger-accident-boarding                (10795),
   passenger-accident-fallen-on-board         (10796),
   passenger-load                             (10797),
   passenger-accident-other                   (10798),
   passenger-sick-or-injured                  (10799),
   right-of-way                               (10800),
   theft                                      (10801),
   theft-of-service                           (10802),
   waiting-to-get-relief-for-schedule-break   (10803),
   waiting-to-get-relief-after-run-is-finished (10804),
   waiting-to-provide-relief                  (10805),
   -- Objects
   -- Misc Items
   unknown-object                             (11009),
   tire                                       (11010),
   rim                                        (11011),
   retread                                    (11012),
   trash                                      (11013),  -- Consider using the
                                                        -- CleanUpItems of IEEE 1512 for
                                                        -- operational needs
   cargo                                      (11014),
   diesel                                     (11015),
   gasoline                                   (11016),  -- RM-060
   anti-freeze                                (11017),
   propane-gas                                (11061),
   alternative-fuel                           (11060),  -- (Implies CNG)
   seat-belts                                 (11018),
   litter-container                           (11019),  -- RG-130  Alt term: Trash
                                                        -- Container
   all-Terrain-vehicle                        (11020),  -- Rl-170
   seaplane                                   (11021),  -- RG-260
   chairlift                                  (11022),  -- RS-100
   fishing-pier                               (11023),  -- RW-160
   telephone                                  (11025),  -- RM-150 See also
                                                        -- Emergency-Telephones 10544
   railroad-cross-buck                        (11024),  -- (Used for Railroad
                                                        -- crossings)
   horn                                       (11048),
   train                                      (11047),  -- The train itself
                                                        -- regardless of the type (not
                                                        -- the mode of transit)
   deer                                       (11049),  -- W11-3
   horse                                      (11051),  -- Use for equestrian as
                                                        -- well
   cattle                                     (11050),  -- W11-4
   golf-cart                                  (11052),  -- W11-10
   services                                   (11056),
   motorist-services                          (11059),  -- Alt text motor services
                                                        -- D9-18
   food-services                              (11053),
   roadside-table                             (11055),
   ambulance-staging-point                    (11054),  -- Use for ambulance station
                                                        -- as well
   -- Shelters-Structures
   fallout                                    (11026),  -- a type of shelter or
                                                        -- structure
   medical                                    (11027),  -- a type of shelter or
                                                        -- structure
   chemical                                   (11028),  -- a type of shelter or
                                                        -- structure
   welfare                                    (11029),  -- a type of shelter or
                                                        -- structure
   decontamination                            (11063),
   evacuation                                 (11030),  -- a type of shelter or
                                                        -- structure
   registration                               (11062),  -- a type of shelter or
                                                        -- structure
   emergency                                  (11064),  --Use only when no other
                                                        -- type is known
   -- Signal States
   left-arrow-signal                          (11031),
   ahead-arrow-signal                         (11032),
   right-arrow-signal                         (11033),
   green-light-signal                         (11034),
   green-arrow-signal                         (11035),
   yellow-light-signal                        (11036),
   yellow-arrow-signal                        (11037),
   red-light-signal                           (11038),
   red-arrow-signal                           (11039),
   extended-green-signal                      (11040),
   advance-arrow-signal                       (11041),
   pedestrian-Signal-Stop                     (11042),  -- Used for dont walk sign
   pedestrian-Signal-Caution                  (11043),  -- Used for dont start to
                                                        -- walk
   pedestrian-Signal-Walk                     (11044),
   pedestrian-Signal-Light                    (11045),  -- Use for light itself
                                                        -- (regardless of state)
   pedestrian-Signal-Time-Display             (11046),  -- Use for count down timer
                                                        -- display
   -- Valid Maneuvers
   prohibit-None-Allowed-LU-LT-L45-S-R45-RT-RU (11264),
   prohibit-RU-Allowed-LU-LT-L45-S-R45-RT     (11265),  -- All Maneuvers allowed
   prohibit-RT-Allowed-LU-LT-L45-S-R45-RU     (11266),
   prohibit-RT-RU-Allowed-LU-LT-L45-S-R45     (11267),
   prohibit-R45-Allowed-LU-LT-L45-S-RT-RU     (11268),
   prohibit-R45-RU-Allowed-LU-LT-L45-S-RT     (11269),
   prohibit-R45-RT-Allowed-LU-LT-L45-S-RU     (11270),
   prohibit-R45-RT-RU-Allowed-LU-LT-L45-S     (11271),  -- Left or Straight Only
                                                        -- (R3-6), Right Turn prohibited
   prohibit-S-Allowed-LU-LT-L45-R45-RT-RU     (11272),
   prohibit-S-RU-Allowed-LU-LT-L45-R45-RT     (11273),
   prohibit-S-RT-Allowed-LU-LT-L45-R45-RU     (11274),
   prohibit-S-RT-RU-Allowed-LU-LT-L45-R45     (11275),
   prohibit-S-R45-Allowed-LU-LT-L45-RT-RU     (11276),
   prohibit-S-R45-RU-Allowed-LU-LT-L45-RT     (11277),
   prohibit-S-R45-RT-Allowed-LU-LT-L45-RU     (11278),
   prohibit-S-R45-RT-RU-Allowed-LU-LT-L45     (11279),
   prohibit-L45-Allowed-LU-LT-S-R45-RT-RU     (11280),  -- Left 45 deg turn
                                                        -- prohibited
   prohibit-L45-RU-Allowed-LU-LT-S-R45-RT     (11281),
   prohibit-L45-RT-Allowed-LU-LT-S-R45-RU     (11282),
   prohibit-L45-RT-RU-Allowed-LU-LT-S-R45     (11283),
   prohibit-L45-R45-Allowed-LU-LT-S-RT-RU     (11284),
   prohibit-L45-R45-RU-Allowed-LU-LT-S-RT     (11285),
   prohibit-L45-R45-RT-Allowed-LU-LT-S-RU     (11286),
   prohibit-L45-R45-RT-RU-Allowed-LU-LT-S     (11287),
   prohibit-L45-S-Allowed-LU-LT-R45-RT-RU     (11288),
   prohibit-L45-S-RU-Allowed-LU-LT-R45-RT     (11289),
   prohibit-L45-S-RT-Allowed-LU-LT-R45-RU     (11290),
   prohibit-L45-S-RT-RU-Allowed-LU-LT-R45     (11291),
   prohibit-L45-S-R45-Allowed-LU-LT-RT-RU     (11292),
   prohibit-L45-S-R45-RU-Allowed-LU-LT-RT     (11293),
   prohibit-L45-S-R45-RT-Allowed-LU-LT-RU     (11294),
   prohibit-L45-S-R45-RT-RU-Allowed-LU-LT     (11295),  -- Left U-Turn and Left Turn
                                                        -- Allowed
   prohibit-LT-Allowed-LU-L45-S-R45-RT-RU     (11296),  -- Left Turn Prohibited
                                                        -- (R3-2)
   prohibit-LT-RU-Allowed-LU-L45-S-R45-RT     (11297),
   prohibit-LT-RT-Allowed-LU-L45-S-R45-RU     (11298),  -- Left and Right Turn
                                                        -- Prohibited  (R3-3), Straight
                                                        -- Only
   prohibit-LT-RT-RU-Allowed-LU-L45-S-R45     (11299),
   prohibit-LT-R45-Allowed-LU-L45-S-RT-RU     (11300),
   prohibit-LT-R45-RU-Allowed-LU-L45-S-RT     (11301),
   prohibit-LT-R45-RT-Allowed-LU-L45-S-RU     (11302),
   prohibit-LT-R45-RT-RU-Allowed-LU-L45-S     (11303),
   prohibit-LT-S-Allowed-LU-L45-R45-RT-RU     (11304),  -- Straight Ahead Prohibited
   prohibit-LT-S-RU-Allowed-LU-L45-R45-RT     (11305),
   prohibit-LT-S-RT-Allowed-LU-L45-R45-RU     (11306),
   prohibit-LT-S-RT-RU-Allowed-LU-L45-R45     (11307),
   prohibit-LT-S-R45-Allowed-LU-L45-RT-RU     (11308),
   prohibit-LT-S-R45-RU-Allowed-LU-L45-RT     (11309),
   prohibit-LT-S-R45-RT-Allowed-LU-L45-RU     (11310),
   prohibit-LT-S-R45-RT-RU-Allowed-LU-L45     (11311),
   prohibit-LT-L45-Allowed-LU-S-R45-RT-RU     (11312),
   prohibit-LT-L45-RU-Allowed-LU-S-R45-RT     (11313),
   prohibit-LT-L45-RT-Allowed-LU-S-R45-RU     (11314),
   prohibit-LT-L45-RT-RU-Allowed-LU-S-R45     (11315),
   prohibit-LT-L45-R45-Allowed-LU-S-RT-RU     (11316),
   prohibit-LT-L45-R45-RU-Allowed-LU-S-RT     (11317),
   prohibit-LT-L45-R45-RT-Allowed-LU-S-RU     (11318),
   prohibit-LT-L45-R45-RT-RU-Allowed-LU-S     (11319),
   prohibit-LT-L45-S-Allowed-LU-R45-RT-RU     (11320),
   prohibit-LT-L45-S-RU-Allowed-LU-R45-RT     (11321),
   prohibit-LT-L45-S-RT-Allowed-LU-R45-RU     (11322),
   prohibit-LT-L45-S-RT-RU-Allowed-LU-R45     (11323),
   prohibit-LT-L45-S-R45-Allowed-LU-RT-RU     (11324),
   prohibit-LT-L45-S-R45-RU-Allowed-LU-RT     (11325),
   prohibit-LT-L45-S-R45-RT-Allowed-LU-RU     (11326),
   prohibit-LT-L45-S-R45-RT-RU-Allowed-LU     (11327),  -- Left U-Turn Allowed
   prohibit-LU-Allowed-LT-L45-S-R45-RT-RU     (11328),  -- Left U-Turn Prohibited
                                                        -- (R3-4)
   prohibit-LU-RU-Allowed-LT-L45-S-R45-RT     (11329),
   prohibit-LU-RT-Allowed-LT-L45-S-R45-RU     (11330),
   prohibit-LU-RT-RU-Allowed-LT-L45-S-R45     (11331),
   prohibit-LU-R45-Allowed-LT-L45-S-RT-RU     (11332),
   prohibit-LU-R45-RU-Allowed-LT-L45-S-RT     (11333),
   prohibit-LU-R45-RT-Allowed-LT-L45-S-RU     (11334),
   prohibit-LU-R45-RT-RU-Allowed-LT-L45-S     (11335),
   prohibit-LU-S-Allowed-LT-L45-R45-RT-RU     (11336),
   prohibit-LU-S-RU-Allowed-LT-L45-R45-RT     (11337),
   prohibit-LU-S-RT-Allowed-LT-L45-R45-RU     (11338),
   prohibit-LU-S-RT-RU-Allowed-LT-L45-R45     (11339),
   prohibit-LU-S-R45-Allowed-LT-L45-RT-RU     (11340),
   prohibit-LU-S-R45-RU-Allowed-LT-L45-RT     (11341),
   prohibit-LU-S-R45-RT-Allowed-LT-L45-RU     (11342),
   prohibit-LU-S-R45-RT-RU-Allowed-LT-L45     (11343),
   prohibit-LU-L45-Allowed-LT-S-R45-RT-RU     (11344),
   prohibit-LU-L45-RU-Allowed-LT-S-R45-RT     (11345),
   prohibit-LU-L45-RT-Allowed-LT-S-R45-RU     (11346),
   prohibit-LU-L45-RT-RU-Allowed-LT-S-R45     (11347),
   prohibit-LU-L45-R45-Allowed-LT-S-RT-RU     (11348),
   prohibit-LU-L45-R45-RU-Allowed-LT-S-RT     (11349),
   prohibit-LU-L45-R45-RT-Allowed-LT-S-RU     (11350),
   prohibit-LU-L45-R45-RT-RU-Allowed-LT-S     (11351),  -- Left Turn and Straight
                                                        -- Ahead Only
   prohibit-LU-L45-S-Allowed-LT-R45-RT-RU     (11352),
   prohibit-LU-L45-S-RU-Allowed-LT-R45-RT     (11353),
   prohibit-LU-L45-S-RT-Allowed-LT-R45-RU     (11354),
   prohibit-LU-L45-S-RT-RU-Allowed-LT-R45     (11355),
   prohibit-LU-L45-S-R45-Allowed-LT-RT-RU     (11356),
   prohibit-LU-L45-S-R45-RU-Allowed-LT-RT     (11357),  -- Left Turn and Right Turn
                                                        -- Only
   prohibit-LU-L45-S-R45-RT-Allowed-LT-RU     (11358),
   prohibit-LU-L45-S-R45-RT-RU-Allowed-LT     (11359),  -- Left Turn Only  (R3-5)
   prohibit-LU-LT-Allowed-L45-S-R45-RT-RU     (11360),  -- Left U-Turn and Left Turn
                                                        -- Prohibited  (R3-18)
   prohibit-LU-LT-RU-Allowed-L45-S-R45-RT     (11361),
   prohibit-LU-LT-RT-Allowed-L45-S-R45-RU     (11362),
   prohibit-LU-LT-RT-RU-Allowed-L45-S-R45     (11363),
   prohibit-LU-LT-R45-Allowed-L45-S-RT-RU     (11364),
   prohibit-LU-LT-R45-RU-Allowed-L45-S-RT     (11365),
   prohibit-LU-LT-R45-RT-Allowed-L45-S-RU     (11366),
   prohibit-LU-LT-R45-RT-RU-Allowed-L45-S     (11367),
   prohibit-LU-LT-S-Allowed-L45-R45-RT-RU     (11368),
   prohibit-LU-LT-S-RU-Allowed-L45-R45-RT     (11369),
   prohibit-LU-LT-S-RT-Allowed-L45-R45-RU     (11370),
   prohibit-LU-LT-S-RT-RU-Allowed-L45-R45     (11371),
   prohibit-LU-LT-S-R45-Allowed-L45-RT-RU     (11372),
   prohibit-LU-LT-S-R45-RU-Allowed-L45-RT     (11373),
   prohibit-LU-LT-S-R45-RT-Allowed-L45-RU     (11374),
   prohibit-LU-LT-S-R45-RT-RU-Allowed-L45     (11375),
   prohibit-LU-LT-L45-Allowed-S-R45-RT-RU     (11376),  -- Right Turn or Straight
                                                        -- Only
   prohibit-LU-LT-L45-RU-Allowed-S-R45-RT     (11377),
   prohibit-LU-LT-L45-RT-Allowed-S-R45-RU     (11378),
   prohibit-LU-LT-L45-RT-RU-Allowed-S-R45     (11379),
   prohibit-LU-LT-L45-R45-Allowed-S-RT-RU     (11380),
   prohibit-LU-LT-L45-R45-RU-Allowed-S-RT     (11381),
   prohibit-LU-LT-L45-R45-RT-Allowed-S-RU     (11382),
   prohibit-LU-LT-L45-R45-RT-RU-Allowed-S     (11383),  -- Straight Ahead Only
                                                        -- (R3-5a)
   prohibit-LU-LT-L45-S-Allowed-R45-RT-RU     (11384),
   prohibit-LU-LT-L45-S-RU-Allowed-R45-RT     (11385),
   prohibit-LU-LT-L45-S-RT-Allowed-R45-RU     (11386),
   prohibit-LU-LT-L45-S-RT-RU-Allowed-R45     (11387),
   prohibit-LU-LT-L45-S-R45-Allowed-RT-RU     (11388),
   prohibit-LU-LT-L45-S-R45-RU-Allowed-RT     (11389),  -- Right Turn Only
   prohibit-LU-LT-L45-S-R45-RT-Allowed-RU     (11390),
   prohibit-LU-LT-L45-S-R45-RT-RU-Allowed-None (11391),  -- All Maneuvers are
                                                        -- Prohibited
   -- Large Numbers
   n1-16th                                    (11521),  -- The fraction 1/16th
   n1-10th                                    (11522),  -- The fraction 1/10th
   n1-8th                                     (11523),  -- The fraction 1/8th
   n1-4th                                     (11524),  -- The fraction 1/4th
   n1-3rd                                     (11525),  -- The fraction 1/3rd
   n1-2                                       (11526),  -- The fraction 1/2
   n3-4                                       (11527),  -- The fraction 3/4th
   n300                                       (11531),
   n350                                       (11532),
   n400                                       (11533),
   n450                                       (11534),
   n500                                       (11535),
   n550                                       (11536),
   n600                                       (11537),
   n650                                       (11538),
   n700                                       (11539),
   n750                                       (11540),
   n800                                       (11541),
   n850                                       (11542),
   n900                                       (11543),
   n950                                       (11544),
   n1000                                      (11545),
   n1100                                      (11546),
   n1200                                      (11547),
   n1300                                      (11548),
   n1400                                      (11549),
   n1500                                      (11550),
   n1600                                      (11551),
   n1700                                      (11552),
   n1800                                      (11553),
   n1900                                      (11554),
   n2000                                      (11555),
   n2100                                      (11556),
   n2200                                      (11557),
   n2300                                      (11558),
   n2400                                      (11559),
   n2500                                      (11560),
   n2600                                      (11561),
   n2700                                      (11562),
   n2800                                      (11563),
   n2900                                      (11564),
   n3000                                      (11565),
   n3500                                      (11566),
   n4000                                      (11567),
   n4500                                      (11568),
   n5000                                      (11569),
   n5500                                      (11570),
   n6000                                      (11571),
   n6500                                      (11572),
   n7000                                      (11573),
   n7500                                      (11574),
   n8000                                      (11575),
   n8500                                      (11576),
   n9000                                      (11577),
   n9500                                      (11578),
   n10000                                     (11579),
   n11000                                     (11580),
   n12000                                     (11581),
   n13000                                     (11582),
   n14000                                     (11583),
   n15000                                     (11584),
   n16000                                     (11585),
   n17000                                     (11586),
   n18000                                     (11587),
   n19000                                     (11588),
   n20000                                     (11589),
   n21000                                     (11590),
   n22000                                     (11591),
   n23000                                     (11592),
   n24000                                     (11593),
   n25000                                     (11594),
   n26000                                     (11595),
   n27000                                     (11596),
   n28000                                     (11597),
   n29000                                     (11598),
   n30000                                     (11599),
   n35000                                     (11600),
   n40000                                     (11601),
   n45000                                     (11602),
   n50000                                     (11603),
   n55000                                     (11604),
   n60000                                     (11605),
   n65000                                     (11606),
   n70000                                     (11607),
   n75000                                     (11608),
   n80000                                     (11609),
   n85000                                     (11610),
   n90000                                     (11611),
   n95000                                     (11612),
   n100000                                    (11613),
   -- Named Objects
   name-follows                               (11777),  -- Used for other types of
                                                        -- named objects to delimit name
   freeway                                    (11778),  -- Typically followed by
                                                        -- name
   us-Route                                   (11779),  -- Typically followed by
                                                        -- name, M1-4
   state-Route                                (11780),  -- Typically followed by
                                                        -- name, M1-5
   interstate                                 (11781),  -- Typically followed by
                                                        -- name, M1-1
   business-Loop                              (11782),  -- Typically followed by
                                                        -- name, M1-2, M4-3
   spur                                       (11797),  -- Typically followed by
                                                        -- name, M1-3
   junction                                    (11798),  -- Typically followed by
                                                        -- names, M2-1, M2-2
   alternative                                (11783),  -- Typically followed by
                                                        -- name, M4-1, M4-1a
   county-Route                               (11784),  -- Typically followed by
                                                        -- name, M1-6
   forest-Route                               (11785),  -- Typically followed by
                                                        -- name, M1-7
   farm-to-Market-Route                       (11786),  -- Typically followed by
                                                        -- name
   eisenhower-Interstate-System               (11787),  -- Typically followed by
                                                        -- name, M1-10
   americas-Byways                            (11788),  -- Typically followed by
                                                        -- name, Alt term: National
                                                        -- Scenic Byways
   national-Network-Route                     (11789),  -- Typically followed by
                                                        -- name
   scenic-Area                                (11790),  -- Typically followed by
                                                        -- name
   parking-Area                               (11791),  -- Typically followed by
                                                        -- name
   weight-Station                             (11792),  -- Typically followed by
                                                        -- name
   road                                       (11793),  -- Typically followed by
                                                        -- name (all types of roads and
                                                        -- streets not otherwise listed
                                                        -- above)
   exit                                       (11794),  -- Typically followed by
                                                        -- name
   historical-route                           (11795),  -- Typically followed by
                                                        -- name
   state-line                                 (11796),  -- Preceded by a state name
                                                        -- I-2
   bicycle-route                               (11799),  -- Typically followed by
                                                        -- name, M1-8
   bicycle-interstate-route                    (11800),  -- Typically followed by
                                                        -- name, M1-9
   national-park                              (11801),  -- Typically preceded by
                                                        -- name, D7-1, D7-2
   -- Recreational Objects and Activities
   -- General Items
   bear-viewing-area                          (12033),  -- RG-020
   deer-viewing-area                          (12034),  -- RG-040
   drinking-water                             (12035),  -- RG-050
   environmental-study-area                   (12036),  -- RG-060
   falling-rocks                              (12037),  -- RG-070 See also ITIS
                                                        -- code: Rockfall 1309
   firearms                                   (12038),  -- RG-080
   leashed-pets                               (12039),  -- RG-110
   point-of-interest                          (12040),  -- RG-160
   smoking                                    (12041),  -- RG-180
   dog                                        (12042),  -- RG-240
   tent-camping                               (12043),  -- RM-010
   trailer-camping                            (12044),  -- RM-020
   first-aid                                  (12045),  -- RM-040
   handicapped                                (12046),  -- RM-080
   mechanic                                   (12047),  -- RM-100
   trailer-sanitary-station                   (12048),  -- RM-160  Alt: Trailer
                                                        -- Waste Station
   viewing-area                               (12049),  -- RM-170
   scenic-overlook                            (12095),  -- For D6-2
   campfire                                   (12050),  -- RA-030
   locker                                     (12051),  -- RA-070
   sleeping                                   (12052),  -- RA-110 As in Sleeping
                                                        -- Shelter
   trail                                      (12053),  -- RA-120 As in Trail
                                                        -- Shelter
   climbing                                   (12054),  -- RL-020
   rock-climbing                              (12055),  -- RL-030
   hunting                                    (12056),  -- RL-040
   playground                                 (12057),  -- RL-050
   rock-collecting                            (12058),  -- RL-060
   spelunking                                 (12059),  -- RL-070
   bicycle-trail                              (12060),  -- RL-090
   hiking-trail                               (12061),  -- RL-100
   horse-trail                                (12062),  -- RL-110
   trail-interpretive-auto                    (12063),  -- RL-120
   trail-interpretive-pedestrian              (12064),  -- RL-130
   trail-road-for-4WD-vehicles                (12065),  -- RL-140
   trail-for-trail-bikes                      (12066),  -- RL-150
   archer                                     (12067),  -- RL-190
   hang-glider                                (12068),  -- RL-210
   -- Water Related
   boat-tours                                 (12069),  -- RW-010
   canoeing                                   (12070),  -- RW-020
   diving                                     (12071),  -- RW-030
   scuba-diving                               (12072),  -- RW-040
   fishing                                    (12073),  -- RW-050
   marine-recreation-area                     (12074),  -- RW-060
   motorboating                               (12075),  -- RW-070
   boat-ramp                                  (12076),  -- RW-080
   rowboating                                 (12077),  -- RW-090
   sailboating                                (12078),  -- RW-100
   water-skiing                               (12079),  -- RW-110
   surfing                                    (12080),  -- RW-120
   swimming                                   (12081),  -- RW-130
   wading                                     (12082),  -- RW-140
   hand-launch                                (12083),  -- RW-170
   kayak                                      (12084),  -- RW-190
   wind-surf                                  (12085),  -- RW-210
   -- Winter-Snow Related
   ice-skating                                (12086),  -- RS-010
   ski-jumping                                (12087),  -- RS-020
   bobbing                                    (12088),  -- RS-030
   cross-country-skiing                       (12089),  -- RS-040
   downhill-skiing                            (12090),  -- RS-050
   sledding                                   (12091),  -- RS-060
   snowmobiling                               (12092),  -- RS-070
   snowshoeing                                (12093),  -- RS-080
   winter-recreation-area                     (12094),  -- RS-090
   -- Regulatory and Warning Signs
   -- MUTCD Signage Types
   regulatory-sign                            (12289),  -- Followed by sign data
   warning-sign                               (12290),  -- Followed by sign data
   information-sign                           (12291),  -- Followed by sign data
   construction-sign                          (12292),  -- Followed by sign data
   guide-sign                                 (12293),  -- Followed by sign data
   -- MUCTD Basic Signs
   stop                                       (12294),
   yield                                      (12295),
   caution                                    (12330),
   temporary                                  (12331),
   to-oncoming-traffic                        (12296),
   four-way                                   (12297),  -- As in 4-way stop
   all-way                                    (12298),  -- All directions of travel
                                                        -- allowed or all lanes at a
                                                        -- junction
   one-way                                    (12329),  -- One direction of travel
                                                        -- allowed
   -- MUCTD Sign Fragments
   zone                                       (12299),  -- Typically preceded by
                                                        -- type of zone
   narrows                                    (12300),  -- Used as an MUTCD sign,
                                                        -- typically preceded by road
   widens                                     (12301),  -- Used as an MUTCD sign,
                                                        -- typically preceded by road
   reduced                                    (12302),  -- Used as an MUTCD sign,
                                                        -- typically preceded by road or
                                                        -- lane
   combined                                   (12303),
   minimum                                    (12304),
   maximum                                    (12305),
   divided-road                               (12306),  -- Use for divided highway
                                                        -- as well
   double-arrow                               (12307),
   dead-end                                   (12308),
   no-outlet                                  (12309),
   wrong-way                                  (12310),  -- R-5-1a
   do-not-enter                               (12314),  -- R-5-1
   nDetour                                     (12312),  -- Typically followed by
                                                        -- arrows and distance
   chevron                                    (12313),
   -- MUCTD Intersection Graphics
   t-intersection-to-the-side                 (12315),
   t-intersection-oncoming                    (12316),  -- Use for W2-4 graphic
   y-intersection-to-the-side                 (12317),
   y-intersection-oncoming                    (12318),  -- Use for W2-5 graphic
   four-way-divided-highway-crossing          (12319),  -- Use for R6-3 graphic
   t-way-divided-highway-crossing             (12320),  -- Use for R6-3a graphic
   light-rail-divided-highway-crossing        (12321),  -- Use for R15-7 graphic
   light-rail-t-divided-highway-crossing      (12322),  -- Use for R15-7a graphic
   side-road-to-right                         (12323),  -- Use for W2-2R graphic
   side-road-to-left                          (12324),  -- Use for W2-2L graphic
   side-road-to-right-at-angle                (12325),  -- Use for W2-3R graphic
   side-road-to-left-at-angle                 (12326),  -- Use for W2-3L graphic
   entering-roadway-merge                     (12327),  -- Use for W4-5 graphic
   entering-roadway-added-lane                (12328),  -- Use for W4-6 graphic
   -- Small Numbers
   n1                                         (12545),
   n2                                         (12546),
   n3                                         (12547),
   n4                                         (12548),
   n5                                         (12549),
   n6                                         (12550),
   n7                                         (12551),
   n8                                         (12552),
   n9                                         (12553),
   n10                                        (12554),
   n11                                        (12555),
   n12                                        (12556),
   n13                                        (12557),
   n14                                        (12558),
   n15                                        (12559),
   n16                                        (12560),
   n17                                        (12561),
   n18                                        (12562),
   n19                                        (12563),
   n20                                        (12564),
   n21                                        (12565),
   n22                                        (12566),
   n23                                        (12567),
   n24                                        (12568),
   n25                                        (12569),
   n26                                        (12570),
   n27                                        (12571),
   n28                                        (12572),
   n29                                        (12573),
   n30                                        (12574),
   n31                                        (12575),
   n32                                        (12576),
   n33                                        (12577),
   n34                                        (12578),
   n35                                        (12579),
   n36                                        (12580),
   n37                                        (12581),
   n38                                        (12582),
   n39                                        (12583),
   n40                                        (12584),
   n41                                        (12585),
   n42                                        (12586),
   n43                                        (12587),
   n44                                        (12588),
   n45                                        (12589),
   n46                                        (12590),
   n47                                        (12591),
   n48                                        (12592),
   n49                                        (12593),
   n50                                        (12594),
   n51                                        (12595),
   n52                                        (12596),
   n53                                        (12597),
   n54                                        (12598),
   n55                                        (12599),
   n56                                        (12600),
   n57                                        (12601),
   n58                                        (12602),
   n59                                        (12603),
   n60                                        (12604),
   n61                                        (12605),
   n62                                        (12606),
   n63                                        (12607),
   n64                                        (12608),
   n65                                        (12609),
   n66                                        (12610),
   n67                                        (12611),
   n68                                        (12612),
   n69                                        (12613),
   n70                                        (12614),
   n71                                        (12615),
   n72                                        (12616),
   n73                                        (12617),
   n74                                        (12618),
   n75                                        (12619),
   n76                                        (12620),
   n77                                        (12621),
   n78                                        (12622),
   n79                                        (12623),
   n80                                        (12624),
   n81                                        (12625),
   n82                                        (12626),
   n83                                        (12627),
   n84                                        (12628),
   n85                                        (12629),
   n86                                        (12630),
   n87                                        (12631),
   n88                                        (12632),
   n89                                        (12633),
   n90                                        (12634),
   n91                                        (12635),
   n92                                        (12636),
   n93                                        (12637),
   n94                                        (12638),
   n95                                        (12639),
   n96                                        (12640),
   n97                                        (12641),
   n98                                        (12642),
   n99                                        (12643),
   n100                                       (12644),
   n101                                       (12645),
   n102                                       (12646),
   n103                                       (12647),
   n104                                       (12648),
   n105                                       (12649),
   n106                                       (12650),
   n107                                       (12651),
   n108                                       (12652),
   n109                                       (12653),
   n110                                       (12654),
   n111                                       (12655),
   n112                                       (12656),
   n113                                       (12657),
   n114                                       (12658),
   n115                                       (12659),
   n116                                       (12660),
   n117                                       (12661),
   n118                                       (12662),
   n119                                       (12663),
   n120                                       (12664),
   n121                                       (12665),
   n122                                       (12666),
   n123                                       (12667),
   n124                                       (12668),
   n125                                       (12669),
   n126                                       (12670),
   n127                                       (12671),
   n128                                       (12672),
   n129                                       (12673),
   n130                                       (12674),
   n131                                       (12675),
   n132                                       (12676),
   n133                                       (12677),
   n134                                       (12678),
   n135                                       (12679),
   n136                                       (12680),
   n137                                       (12681),
   n138                                       (12682),
   n139                                       (12683),
   n140                                       (12684),
   n141                                       (12685),
   n142                                       (12686),
   n143                                       (12687),
   n144                                       (12688),
   n145                                       (12689),
   n146                                       (12690),
   n147                                       (12691),
   n148                                       (12692),
   n149                                       (12693),
   n150                                       (12694),
   n151                                       (12695),
   n152                                       (12696),
   n153                                       (12697),
   n154                                       (12698),
   n155                                       (12699),
   n156                                       (12700),
   n157                                       (12701),
   n158                                       (12702),
   n159                                       (12703),
   n160                                       (12704),
   n161                                       (12705),
   n162                                       (12706),
   n163                                       (12707),
   n164                                       (12708),
   n165                                       (12709),
   n166                                       (12710),
   n167                                       (12711),
   n168                                       (12712),
   n169                                       (12713),
   n170                                       (12714),
   n171                                       (12715),
   n172                                       (12716),
   n173                                       (12717),
   n174                                       (12718),
   n175                                       (12719),
   n176                                       (12720),
   n177                                       (12721),
   n178                                       (12722),
   n179                                       (12723),
   n180                                       (12724),
   n181                                       (12725),
   n182                                       (12726),
   n183                                       (12727),
   n184                                       (12728),
   n185                                       (12729),
   n186                                       (12730),
   n187                                       (12731),
   n188                                       (12732),
   n189                                       (12733),
   n190                                       (12734),
   n191                                       (12735),
   n192                                       (12736),
   n193                                       (12737),
   n194                                       (12738),
   n195                                       (12739),
   n196                                       (12740),
   n197                                       (12741),
   n198                                       (12742),
   n199                                       (12743),
   n200                                       (12744),
   n201                                       (12745),
   n202                                       (12746),
   n203                                       (12747),
   n204                                       (12748),
   n205                                       (12749),
   n206                                       (12750),
   n207                                       (12751),
   n208                                       (12752),
   n209                                       (12753),
   n210                                       (12754),
   n211                                       (12755),
   n212                                       (12756),
   n213                                       (12757),
   n214                                       (12758),
   n215                                       (12759),
   n216                                       (12760),
   n217                                       (12761),
   n218                                       (12762),
   n219                                       (12763),
   n220                                       (12764),
   n221                                       (12765),
   n222                                       (12766),
   n223                                       (12767),
   n224                                       (12768),
   n225                                       (12769),
   n226                                       (12770),
   n227                                       (12771),
   n228                                       (12772),
   n229                                       (12773),
   n230                                       (12774),
   n231                                       (12775),
   n232                                       (12776),
   n233                                       (12777),
   n234                                       (12778),
   n235                                       (12779),
   n236                                       (12780),
   n237                                       (12781),
   n238                                       (12782),
   n239                                       (12783),
   n240                                       (12784),
   n241                                       (12785),
   n242                                       (12786),
   n243                                       (12787),
   n244                                       (12788),
   n245                                       (12789),
   n246                                       (12790),
   n247                                       (12791),
   n248                                       (12792),
   n249                                       (12793),
   n250                                       (12794),
   n251                                       (12795),
   n252                                       (12796),
   n253                                       (12797),
   n254                                       (12798),
   n255                                       (12799),
   -- States and Territories
   alabama                                    (12801),
   alaska                                     (12802),
   american-Samoa                             (12803),
   arizona                                    (12804),
   arkansas                                   (12805),
   california                                 (12806),
   colorado                                   (12807),
   connecticut                                (12808),
   delaware                                   (12809),
   district-of-Columbia                       (12810),
   florida                                    (12811),
   georgia                                    (12812),
   guam                                       (12813),
   hawaii                                     (12814),
   idaho                                      (12815),
   illinois                                   (12816),
   indiana                                    (12817),
   iowa                                       (12818),
   kansas                                     (12819),
   kentucky                                   (12820),
   louisiana                                  (12821),
   maine                                      (12822),
   maryland                                   (12823),
   massachusetts                              (12824),
   michigan                                   (12825),
   minnesota                                  (12826),
   mississippi                                (12827),
   missouri                                   (12828),
   montana                                    (12829),
   nebraska                                   (12830),
   nevada                                     (12831),
   new-Hampshire                              (12832),
   new-Jersey                                 (12833),
   new-Mexico                                 (12834),
   new-York                                   (12835),
   north-Carolina                             (12836),
   north-Dakota                               (12837),
   northern-Marianas-Islands                  (12838),
   ohio                                       (12839),
   oklahoma                                   (12840),
   oregon                                     (12841),
   pennsylvania                               (12842),
   puerto-rico                                (12843),
   rhode-Island                               (12844),
   south-Carolina                             (12845),
   south-Dakota                               (12846),
   tennessee                                  (12847),
   texas                                      (12848),
   utah                                       (12849),
   vermont                                    (12850),
   virginia                                   (12851),
   virgin-Islands                             (12852),
   washington                                 (12853),
   west-Virginia                              (12854),
   wisconsin                                  (12855),
   wyoming                                    (12856),
   -- Structures
   rest-room                                  (13057),  -- RM-140
   mens-rest-room                             (13058),  -- RA-090
   womens-rest-room                           (13059),  -- RA-100
   family-rest-room                           (13060),  -- RA-150
   dam                                        (13061),  -- RG-030
   fish-hatchery                              (13062),  -- RG-090
   information                                (13063),  -- RG-100
   lighthouse                                 (13064),  -- RG-120
   lookout-tower                              (13065),  -- RG-140
   ranger-station                             (13066),  -- RG-170
   grocery-store                              (13068),  -- RM-070
   lodging                                    (13069),  -- RM-090
   post-office                                (13070),  -- RM-110
   picnic-shelter                             (13072),  -- RM-130
   group-camping                              (13073),  -- RM-210
   group-picnicking                           (13074),  -- RM-220
   n24-hour-pharmacy                          (13075),  -- RM-230
   kennel                                     (13076),  -- RA-050
   laundry-facilities                         (13077),  -- RA-060
   shower-facilities                          (13078),  -- RA-130
   amphitheater                               (13079),  -- RL-010
   stable                                     (13080),  -- RL-080
   hospital                                   (13081),  -- D9-13a or D9-2
   emergency-medical-service-point            (13082),  -- Use for emergency medical
                                                        -- care as well D9-13c
   library                                    (13083),  -- I-8p
   recycling-collection-center                (13084),  -- I-11
   school                                     (13085),  -- Use for S1-1
   -- Street Suffixes
   alley                                      (13313),
   annex                                      (13314),
   arcade                                     (13315),
   avenue                                     (13316),
   bayoo                                      (13317),
   beach                                      (13318),
   bend                                       (13319),
   bluff                                      (13320),
   bottom                                     (13321),
   boulevard                                  (13322),
   branch                                     (13323),
   nBridge                                    (13324),  -- Note use of "n" to avoid
                                                        -- conflict with other entry
   brook                                      (13325),
   burg                                       (13326),
   bypass                                     (13327),
   camp                                       (13328),
   canyon                                     (13329),
   cape                                       (13330),
   causeway                                   (13331),
   nCenter                                    (13332),  --: Note use of "n" to avoid
                                                        -- conflict with other entry
   circle                                     (13333),
   cliff                                      (13334),
   club                                       (13335),
   common                                     (13336),
   corner                                     (13337),
   course                                     (13338),
   court                                      (13339),
   cove                                       (13340),
   creek                                      (13341),
   crescent                                   (13342),
   crest                                      (13343),
   nCrossing                                  (13344),  -- Note use of "n" to avoid
                                                        -- conflict with other entry
   crossroad                                  (13345),
   curve                                      (13346),
   dale                                       (13347),
   nDam                                       (13348),  -- Note use of "n" to avoid
                                                        -- conflict with other entry
   divide                                     (13349),
   drive                                      (13350),
   estate                                     (13351),
   expressway                                 (13352),
   extension                                  (13353),
   fall                                       (13354),
   nFerry                                     (13355),  -- Note use of "n" to avoid
                                                        -- conflict with other entry
   field                                      (13356),
   flat                                       (13357),
   ford                                       (13358),
   forest                                     (13359),
   forge                                      (13360),
   fork                                       (13361),
   fort                                       (13362),
   nFreeway                                   (13363),  -- Note use of "n" to avoid
                                                        -- conflict with other entry
   garden                                     (13364),
   gateway                                    (13365),
   glen                                       (13366),
   green                                      (13367),
   grove                                      (13368),
   harbor                                     (13369),
   haven                                      (13370),
   heights                                    (13371),
   highway                                    (13372),
   nHill                                      (13373),  -- Note use of "n" to avoid
                                                        -- conflict with other entry
   hollow                                     (13374),
   inlet                                      (13375),
   nIsland                                    (13376),  -- Note use of "n" to avoid
                                                        -- conflict with other entry
   isle                                       (13377),  --
   nJunction                                  (13378),  -- Note use of "n" to avoid
                                                        -- conflict with other entry
   key                                        (13379),
   knoll                                      (13380),
   lake                                       (13381),
   land                                       (13382),
   landing                                    (13383),
   nLane                                      (13384),  -- Note use of "n" to avoid
                                                        -- conflict with other entry
   light                                      (13385),
   loaf                                       (13386),
   lock                                       (13387),
   lodge                                      (13388),
   loop                                       (13389),
   mall                                       (13390),
   manor                                      (13391),
   meadow                                     (13392),
   mews                                       (13393),
   mill                                       (13394),
   mission                                    (13395),
   motorway                                   (13396),
   mount                                      (13397),
   mountain                                   (13398),
   neck                                       (13399),
   orchard                                    (13400),
   oval                                       (13401),
   nOverpass                                  (13402),  -- Note use of "n" to avoid
                                                        -- conflict with other entry
   park                                       (13403),
   parkway                                    (13404),
   nPass                                      (13405),  -- Note use of "n" to avoid
                                                        -- conflict with other entry
   passage                                    (13406),
   path                                       (13407),
   pike                                       (13408),
   pine                                       (13409),
   plains                                     (13410),
   plaza                                      (13411),
   point                                      (13412),
   port                                       (13413),
   prairie                                    (13414),
   radial                                     (13415),
   ramp                                       (13416),
   ranch                                      (13417),
   rapid                                      (13418),
   rest                                       (13419),
   ridge                                      (13420),
   river                                      (13421),
   nRoad                                      (13422),  -- Note use of "n" to avoid
                                                        -- conflict with other entry
   route                                      (13423),
   row                                        (13424),
   rue                                        (13425),
   run                                        (13426),
   shoal                                      (13427),
   shore                                      (13428),
   skyway                                     (13429),
   spring                                     (13430),
   nSpur                                      (13431), -- Note use of "n" to avoid
                                                        -- conflict with other entry

   square                                     (13432),
   nStation                                   (13433),  -- Note use of "n" to avoid
                                                        -- conflict with other entry
   stravenue                                  (13434),
   stream                                     (13435),
   street                                     (13436),
   summit                                     (13437),
   terrace                                    (13438),
   throughway                                 (13439),
   trace                                      (13440),
   nTrack                                     (13441),  -- Note use of "n" to avoid
                                                        -- conflict with other entry
   trafficway                                 (13442),
   nTrail                                     (13443),  -- Note use of "n" to avoid
                                                        -- conflict with other entry
   nTunnel                                    (13444),  -- Note use of "n" to avoid
                                                        -- conflict with other entry
   turnpike                                   (13445),
   nUnderpass                                 (13446),  -- Note use of "n" to avoid
                                                        -- conflict with other entry
   union                                      (13447),
   valley                                     (13448),
   viaduct                                    (13449),
   view                                       (13450),
   village                                    (13451),
   ville                                      (13452),
   vista                                      (13453),
   nWalk                                      (13454),  -- Note use of "n" to avoid
                                                        -- conflict with other  entry
   wall                                       (13455),
   way                                        (13456),
   well                                       (13457),
   -- MUTCD Locations
   -- Signage Locations
   ahead                                      (13569),  -- Location and used as
                                                        -- arrow
   here                                       (13570),  -- Location and used as
                                                        -- arrow
   here-to                                    (13571),  -- Followed by specific
                                                        -- object
   here-to-alley                              (13572),
   here-to-corner                             (13573),
   here-to-sign                               (13574),
   between-signs                              (13575),
   between                                    (13633),  -- Followed by object, and,
                                                        -- another object
   this-side-of-street                        (13576),
   this-side-of-sign                          (13577),
   right                                      (13579),
   left                                       (13580),
   begin-point                                (13581),  -- Use for "begins" as well.
                                                        -- Do not use for times/dates
   next                                       (13582),  -- May be followed by a
                                                        -- distance value
   starting-start                             (13611),  -- Do not use for
                                                        -- times/dates
   ends-end                                   (13583),  -- Do not use for
                                                        -- times/dates
   other-Side                                 (13584),
   crossing                                   (13585),
   crosswalks                                 (13586),
   center-strip                               (13587),  -- Alt form: center stripe
   lane                                       (13588),  -- Used for lanes as well
   shelter                                    (13634),  -- Typically preceded by a
                                                        -- specific type
   center                                     (13635),  -- Typically preceded by a
                                                        -- specific type
   -- Signage Arrows
   hill                                       (13589),
   both-ways-left-and-right                   (13590),
   both-ways-45-degree-angle-tilting-right    (13591),
   both-ways-45-degree-angle-tilting-left     (13592),
   both-directions-of-travel                  (13593),  -- As in Centerline - left
                                                        -- turn arrows - both directions
                                                        -- of travel or for two-way
                                                        -- traffic
   left-arrow                                 (13610),
   left-turn                                  (13594),  -- For W1R
   left-45-degree-arrow                       (13595),
   left-45-degree-turn                        (13596),
   ahead-and-to-the-left                      (13597),
   ahead-and-to-the-left-at-a-45-degree-angle (13598),
   right-arrow                                (13609),
   right-turn                                 (13599),  -- For W1R
   right-45-degree-arrow                      (13600),  -- For W1-2
   right-45-degree-turn                       (13601),
   ahead-and-to-the-right                     (13602),
   ahead-and-to-the-right-at-a-45-degree-angle (13603),
   downward-left-45-degree                    (13604),
   downward-right-45-degree                   (13605),
   downward-left-and-right-45-degree          (13606),
   reverse-turn-to-right                      (13636),  -- For W1-3R
   reverse-turn-to-left                       (13637),  -- For W1-3L
   reverse-curve-to-right                     (13638),  -- For W1-4R
   reverse-curve-to-left                      (13639),  -- For W1-4L
   two-lane-reverse-curve-to-right            (13623),  -- For W1-4bR
   two-lane-reverse-curve-to-left             (13624),  -- For W1-4bL
   three-lane-reverse-curve-to-right          (13625),  -- For W1-4cR
   three-lane-reverse-curve-to-left           (13626),  -- For W1-4cL
   winding-road-to-right                      (13640),  -- For W1-5R
   winding-road-to-left                       (13641),  -- For W1-5L
   chevron-right                              (13613),  -- For W1-8R
   chevron-left                               (13614),  -- For W1-8L
   right-turn-with-junction                   (13615),  -- For horizontal alignment
                                                        -- right W1-10R
   left-turn-with-junction                    (13616),  -- For horizontal alignment
                                                        -- left W1-10L
   hairpin-right                              (13617),  -- For W1-11
   hairpin-left                               (13618),  -- For W1-11
   truck-rollover-right                       (13619),  -- For W1-13
   truck-rollover-left                        (13620),
   n270-degree-turn-right                    (13621),  -- For W1-15
   n270-degree-turn-left                     (13622),
   double-reverse-curve-to-right              (13627),  -- For W24-1R
   double-reverse-curve-to-left               (13628),  -- For W24-1L
   two-lane-double-reverse-curve-to-right     (13629),  -- For W24-1aR
   two-lane-double-reverse-curve-to-left      (13630),  -- For W24-1aL
   three-lane-double-reverse-curve-to-right   (13631),  -- For W24-1bR
   three-lane-double-reverse-curve-to-left    (13632)   -- For W24-1bL
   } (0..65535)


LaneRoadway ::= INTEGER  {
   -- Lanes
   all-roadways               (8193),  -- Used as the default value
   through-lanes              (8194),
   left-lane                  (8195),
   right-lane                 (8196),
   center-lane                (8197),
   middle-lanes               (8198),
   middle-two-lanes           (8199),
   right-turning-lanes        (8200),
   left-turning-lanes         (8201),
   upper-deck-lanes           (8236),
   lower-deck-lanes           (8237),
   reversible-lanes           (8238),
   right-exit-lanes           (8239),
   left-exit-lanes            (8240),
   right-merging-lanes        (8241),
   left-merging-lanes         (8242),
   -- Ramps
   right-exit-ramp            (8202),
   right-second-exit-ramp     (8243),
   right-entrance-ramp        (8203),
   right-second-entrance-ramp (8245),
   left-exit-ramp             (8204),
   left-second-exit-ramp      (8244),
   left-entrance-ramp         (8205),
   left-second-entrance-ramp  (8246),
   escape-ramp                (8234),  -- A truck feature on steep downgrades common in
                                       -- both Alaska and elsewhere.
   -- Shoulders
   hard-shoulder              (8206),
   soft-shoulder              (8207),
   right-shoulder             (8208),
   left-shoulder              (8209),
   median                     (8252),
   sidewalk                   (8251),
   -- Other
   highways                   (8235),
   right-hand-parallel-lanes  (8210),  -- Alternative Rendering: right-hand frontage
                                       -- road
   left-hand-parallel-lanes   (8211),  -- Alternative Rendering: left-hand frontage road
   connecting-lanes           (8212),
   express-lanes              (8213),
   local-lanes                (8214),
   toll-lanes                 (8215),
   electronic-toll-lanes      (8216),
   toll-plaza                 (8217),
   inspection-lane            (8218),  -- Alternative Rendering: Border patrol
                                       -- inspection lane
   hOV-lanes                  (8219),  -- Use when 2+ or 3+ is unknown and for HOV in
                                       -- general
   bus-lanes                  (8220),
   carpool-lanes              (8221),
   truck-lanes                (8222),
   emergency-lanes            (8223),
   passing-lanes              (8224),
   climbing-lanes             (8225),
   slow-lane                  (8226),  -- Alternative Rendering: Crawler lane
   service-road               (8227),  -- Alternative Rendering: Frontage Road
   cycle-lane                 (8228),  -- Use for bicycle lanes of all types
   tracks                     (8250),  -- Use for light rail and transit uses, may
                                       -- have count of tracks
   -- Bridges, Tunnels
   bridge                     (8229),
   overpass                   (8230),
   elevated-lanes             (8231),
   underpass                  (8232),
   tunnel                     (8233),  -- Use for RG-200
   -- Lanes Groups
   all-exit-lanes             (8247),
   all-entry-lanes            (8248),
   either-shoulder            (8249),
   shoulder-work              (8253)   -- Use for W21-5 as well
   } (0..65535)


LargeNumbers ::= INTEGER  {
   n1-16th (11521),  -- The fraction 1/16th
   n1-10th (11522),  -- The fraction 1/10th
   n1-8th  (11523),  -- The fraction 1/8th
   n1-4th  (11524),  -- The fraction 1/4th
   n1-3rd  (11525),  -- The fraction 1/3rd
   n1-2    (11526),  -- The fraction 1/2
   n3-4    (11527),  -- The fraction 3/4th
   n300    (11531),
   n350    (11532),
   n400    (11533),
   n450    (11534),
   n500    (11535),
   n550    (11536),
   n600    (11537),
   n650    (11538),
   n700    (11539),
   n750    (11540),
   n800    (11541),
   n850    (11542),
   n900    (11543),
   n950    (11544),
   n1000   (11545),
   n1100   (11546),
   n1200   (11547),
   n1300   (11548),
   n1400   (11549),
   n1500   (11550),
   n1600   (11551),
   n1700   (11552),
   n1800   (11553),
   n1900   (11554),
   n2000   (11555),
   n2100   (11556),
   n2200   (11557),
   n2300   (11558),
   n2400   (11559),
   n2500   (11560),
   n2600   (11561),
   n2700   (11562),
   n2800   (11563),
   n2900   (11564),
   n3000   (11565),
   n3500   (11566),
   n4000   (11567),
   n4500   (11568),
   n5000   (11569),
   n5500   (11570),
   n6000   (11571),
   n6500   (11572),
   n7000   (11573),
   n7500   (11574),
   n8000   (11575),
   n8500   (11576),
   n9000   (11577),
   n9500   (11578),
   n10000  (11579),
   n11000  (11580),
   n12000  (11581),
   n13000  (11582),
   n14000  (11583),
   n15000  (11584),
   n16000  (11585),
   n17000  (11586),
   n18000  (11587),
   n19000  (11588),
   n20000  (11589),
   n21000  (11590),
   n22000  (11591),
   n23000  (11592),
   n24000  (11593),
   n25000  (11594),
   n26000  (11595),
   n27000  (11596),
   n28000  (11597),
   n29000  (11598),
   n30000  (11599),
   n35000  (11600),
   n40000  (11601),
   n45000  (11602),
   n50000  (11603),
   n55000  (11604),
   n60000  (11605),
   n65000  (11606),
   n70000  (11607),
   n75000  (11608),
   n80000  (11609),
   n85000  (11610),
   n90000  (11611),
   n95000  (11612),
   n100000 (11613)
   } (0..65535)


MobileSituation ::= INTEGER  {
   abnormal-load                                   (2049),
   wide-load                                       (2050),
   long-load                                       (2051),
   slow-vehicle                                    (2052),
   farm-equipment                                  (2053),
   horse-drawn-vehicles                            (2054),
   overheight-load                                 (2055),
   overweight-load                                 (2056),
   tracked-vehicle                                 (2057),
   vehicle-carrying-hazardous-materials            (2058),
   slow-moving-maintenance-vehicle                 (2059),  -- Hint: mowing, line
                                                            -- stripping, sweepers, etc.
   convoy                                          (2060),
   military-convoy                                 (2061),
   refugee-convoy                                  (2062),
   motorcade                                       (2063),
   mobile-situation-repositioning                  (2064),
   winter-maintenance-vehicles                     (2065),
   snowplows                                       (2066),
   -- Cancel Types
   slow-moving-maintenance-vehicle-warning-cleared (2172),
   exceptional-load-warning-cleared                (2173),
   hazardous-load-warning-cleared                  (2174),
   convoy-cleared                                  (2175)
   } (0..65535)
   -- Used for events which are mobile along the network


MUTCDLocations ::= INTEGER  {
   -- Signage Locations
   ahead                                       (13569),  -- Location and used as
                                                         -- arrow
   here                                        (13570),  -- Location and used as
                                                         -- arrow
   here-to                                     (13571),  -- Followed by specific
                                                         -- object
   here-to-alley                               (13572),
   here-to-corner                              (13573),
   here-to-sign                                (13574),
   between-signs                               (13575),
   between                                     (13633),  -- Followed by object, and,
                                                         -- another object
   this-side-of-street                         (13576),
   this-side-of-sign                           (13577),
   right                                       (13579),
   left                                        (13580),
   begin-point                                 (13581),  -- Use for "begins" as
                                                         -- well. Do not use for
                                                         -- times/dates
   next                                        (13582),  -- May be followed by a
                                                         -- distance value
   starting-start                              (13611),  -- Do not use for
                                                         -- times/dates
   ends-end                                    (13583),  -- Do not use for
                                                         -- times/dates
   other-Side                                  (13584),
   crossing                                    (13585),
   crosswalks                                  (13586),
   center-strip                                (13587),  -- Alt form: center stripe
   lane                                        (13588),  -- Used for lanes as well
   shelter                                     (13634),  -- Typically preceded by a
                                                         -- specific type
   center                                      (13635),  -- Typically preceded by a
                                                         -- specific type
   -- Signage Arrows
   hill                                        (13589),
   both-ways-left-and-right                    (13590),
   both-ways-45-degree-angle-tilting-right     (13591),
   both-ways-45-degree-angle-tilting-left      (13592),
   both-directions-of-travel                   (13593),  -- As in Centerline - left
                                                         -- turn arrows - both directions
                                                         -- of travel or for two-way
                                                         -- traffic
   left-arrow                                  (13610),
   left-turn                                   (13594),  -- For W1R
   left-45-degree-arrow                        (13595),
   left-45-degree-turn                         (13596),
   ahead-and-to-the-left                       (13597),
   ahead-and-to-the-left-at-a-45-degree-angle  (13598),
   right-arrow                                 (13609),
   right-turn                                  (13599),  -- For W1R
   right-45-degree-arrow                       (13600),  -- For W1-2
   right-45-degree-turn                        (13601),
   ahead-and-to-the-right                      (13602),
   ahead-and-to-the-right-at-a-45-degree-angle (13603),
   downward-left-45-degree                     (13604),
   downward-right-45-degree                    (13605),
   downward-left-and-right-45-degree           (13606),
   reverse-turn-to-right                       (13636),  -- For W1-3R
   reverse-turn-to-left                        (13637),  -- For W1-3L
   reverse-curve-to-right                      (13638),  -- For W1-4R
   reverse-curve-to-left                       (13639),  -- For W1-4L
   two-lane-reverse-curve-to-right             (13623),  -- For W1-4bR
   two-lane-reverse-curve-to-left              (13624),  -- For W1-4bL
   three-lane-reverse-curve-to-right           (13625),  -- For W1-4cR
   three-lane-reverse-curve-to-left            (13626),  -- For W1-4cL
   winding-road-to-right                       (13640),  -- For W1-5R
   winding-road-to-left                        (13641),  -- For W1-5L
   chevron-right                               (13613),  -- For W1-8R
   chevron-left                                (13614),  -- For W1-8L
   right-turn-with-junction                    (13615),  -- For horizontal alignment
                                                         -- right W1-10R
   left-turn-with-junction                     (13616),  -- For horizontal alignment
                                                         -- left W1-10L
   hairpin-right                               (13617),  -- For W1-11
   hairpin-left                                (13618),  -- For W1-11
   truck-rollover-right                        (13619),  -- For W1-13
   truck-rollover-left                         (13620),
   n270-degree-turn-right                     (13621),  -- For W1-15
   n270-degree-turn-left                      (13622),
   double-reverse-curve-to-right               (13627),  -- For W24-1R
   double-reverse-curve-to-left                (13628),  -- For W24-1L
   two-lane-double-reverse-curve-to-right      (13629),  -- For W24-1aR
   two-lane-double-reverse-curve-to-left       (13630),  -- For W24-1aL
   three-lane-double-reverse-curve-to-right    (13631),  -- For W24-1bR
   three-lane-double-reverse-curve-to-left     (13632)   -- For W24-1bL
   } (0..65535)


NamedObjects ::= INTEGER  {
   name-follows                 (11777),  -- Used for other types of named objects
                                          -- to delimit name
   freeway                      (11778),  -- Typically followed by name
   us-Route                     (11779),  -- Typically followed by name, M1-4
   state-Route                  (11780),  -- Typically followed by name, M1-5
   interstate                   (11781),  -- Typically followed by name, M1-1
   business-Loop                (11782),  -- Typically followed by name, M1-2, M4-3
   spur                         (11797),  -- Typically followed by name, M1-3
   junction                     (11798),  -- Typically followed by names, M2-1, M2-2
   alternative                  (11783),  -- Typically followed by name, M4-1, M4-1a
   county-Route                 (11784),  -- Typically followed by name, M1-6
   forest-Route                 (11785),  -- Typically followed by name, M1-7
   farm-to-Market-Route         (11786),  -- Typically followed by name
   eisenhower-Interstate-System (11787),  -- Typically followed by name, M1-10
   americas-Byways              (11788),  -- Typically followed by name, Alt term:
                                          -- National Scenic Byways
   national-Network-Route       (11789),  -- Typically followed by name
   scenic-Area                  (11790),  -- Typically followed by name
   parking-Area                 (11791),  -- Typically followed by name
   weight-Station               (11792),  -- Typically followed by name
   road                         (11793),  -- Typically followed by name (all types
                                          -- of roads and streets not otherwise listed
                                          -- above)
   exit                         (11794),  -- Typically followed by name
   historical-route             (11795),  -- Typically followed by name
   state-line                   (11796),  -- Preceded by a state name I-2
   bicycle-route                (11799),  -- Typically followed by name, M1-8
   bicycle-interstate-route     (11800),  -- Typically followed by name, M1-9
   national-park                (11801)   -- Typically preceded by name, D7-1, D7-2
   } (0..65535)


Objects ::= INTEGER  {
   -- Misc Items
   unknown-object                 (11009),
   tire                           (11010),
   rim                            (11011),
   retread                        (11012),
   trash                          (11013),  -- Consider using the CleanUpItems of IEEE
                                            -- 1512 for operational needs
   cargo                          (11014),
   diesel                         (11015),
   gasoline                       (11016),  -- RM-060
   anti-freeze                    (11017),
   propane-gas                    (11061),
   alternative-fuel               (11060),  -- (Implies CNG)
   seat-belts                     (11018),
   litter-container               (11019),  -- RG-130  Alt term: Trash Container
   all-Terrain-vehicle            (11020),  -- Rl-170
   seaplane                       (11021),  -- RG-260
   chairlift                      (11022),  -- RS-100
   fishing-pier                   (11023),  -- RW-160
   telephone                      (11025),  -- RM-150 See also Emergency-Telephones
                                            -- 10544
   railroad-cross-buck            (11024),  -- (Used for Railroad crossings)
   horn                           (11048),
   train                          (11047),  -- The train itself regardless of the
                                            -- type (not the mode of transit)
   deer                           (11049),  -- W11-3
   horse                          (11051),  -- Use for equestrian as well
   cattle                         (11050),  -- W11-4
   golf-cart                      (11052),  -- W11-10
   services                       (11056),
   motorist-services              (11059),  -- Alt text motor services D9-18
   food-services                  (11053),
   roadside-table                 (11055),
   ambulance-staging-point        (11054),  -- Use for ambulance station as well
   -- Shelters-Structures
   fallout                        (11026),  -- a type of shelter or structure
   medical                        (11027),  -- a type of shelter or structure
   chemical                       (11028),  -- a type of shelter or structure
   welfare                        (11029),  -- a type of shelter or structure
   decontamination                (11063),
   evacuation                     (11030),  -- a type of shelter or structure
   registration                   (11062),  -- a type of shelter or structure
   emergency                      (11064),  --Use only when no other type is known
   -- Signal States
   left-arrow-signal              (11031),
   ahead-arrow-signal             (11032),
   right-arrow-signal             (11033),
   green-light-signal             (11034),
   green-arrow-signal             (11035),
   yellow-light-signal            (11036),
   yellow-arrow-signal            (11037),
   red-light-signal               (11038),
   red-arrow-signal               (11039),
   extended-green-signal          (11040),
   advance-arrow-signal           (11041),
   pedestrian-Signal-Stop         (11042),  -- Used for dont walk sign
   pedestrian-Signal-Caution      (11043),  -- Used for dont start to walk
   pedestrian-Signal-Walk         (11044),
   pedestrian-Signal-Light        (11045),  -- Use for light itself (regardless of
                                            -- state)
   pedestrian-Signal-Time-Display (11046)   -- Use for count down timer display
   } (0..65535)


Obstruction ::= INTEGER  {
   -- General
   obstruction-on-roadway              (1281),
   object-on-roadway                   (1282),
   objects-falling-from-moving-vehicle (1283),
   debris-on-roadway                   (1284),
   storm-damage                        (1285),
   -- People
   people-on-roadway                   (1286),
   bicyclists-on-roadway               (1287),
   sightseers-obstructing-access       (1288),
   large-numbers-of-visitors           (1289),
   -- Animals
   animal-on-roadway                   (1290),
   large-animal-on-roadway             (1291),
   herd-of-animals-on-roadway          (1292),
   animal-struck                       (1293),
   -- Specific Items
   advertising-signs                   (1315),  -- Used for illegal signage as well
   fallen-trees                        (1294),
   over-turned-trees                   (1311),
   tree-limbs                          (1312),
   utility-pole-down                   (1314),
   downed-power-lines                  (1295),  -- Alternative Rendering: fallen power
                                                -- lines
   downed-cables                       (1296),  -- Alternative Rendering: fallen cables
   subsidence                          (1297),  -- Alternative Rendering: road collapse
   road-surface-collapse               (1298),
   frost-jacking                       (1317),  -- A unique Alaska problem caused by
                                                -- culverts or other features jacking out
                                                -- of ground due to freezing
   frost-heave                         (1316),  -- A large standing wave of soil under
                                                -- pavement due to frost action
   pavement-buckled                    (1299),
   pothole                             (1300),
   flooding                            (1301),
   broken-water-main                   (1302),
   collapsed-sewer                     (1303),
   wash-out                            (1319),  -- What can happen to roads
   washboard                           (1318),  -- A term for rough road or unpaved roads
   sewer-overflow                      (1304),
   gas-leak                            (1305),
   snowmelt                            (1306),  -- Hint: Typically used as a cause
   mudslide                            (1307),
   avalanche                           (1308),  -- Possibly a disaster as well
   rockfall                            (1309),
   landslide                           (1310),
   -- Cancel Types
   clearance-work                      (1406),
   obstruction-cleared                 (1407)
   } (0..65535)
   -- note singular spelling


ParkingInformation ::= INTEGER  {
   normal-parking-restrictions-lifted    (4097),  -- Hint: used when a PARKING
                                                  -- restriction is lifted (overnight
                                                  -- parking allowed during event)  Not
                                                  -- to be used as a default for this
                                                  -- category
   parking-meter-restrictions-lifted     (4098),  -- Hint: used when a METER restriction
                                                  -- is lifted (metered parking free
                                                  -- during event)
   special-parking-restrictions-in-force (4099),
   full-parking-lot                      (4100),
   full-parking-garage                   (4101),
   all-parking-lots-full                 (4102),
   no-parking-spaces-available           (4103),
   only-a-few-spaces-available           (4104),
   spaces-available                      (4105),  -- Typically preceded by a # value
   no-parking                            (4106),  -- Typically followed by restriction
                                                  -- data
   parking-on-one-side-of-street-only    (4107),
   parking-on-both-sides-of-street       (4108),
   parallel-parking-only                 (4109),
   parking-meters-not-available          (4110),
   use-of-parking-meters-restricted      (4111),
   event-parking                         (4112),
   handicapped-parking                   (4113),
   long-term-parking                     (4114),
   overnight-parking                     (4115),
   short-term-parking                    (4116),
   parking-by-permit-only                (4117),
   emergency-parking-only                (4118),
   emergency-stopping-only               (4119),
   parking                               (4120),  -- Typically followed by
                                                  -- restriction data
   stopping                              (4121),  -- Typically followed by
                                                  -- restriction data
   standing                              (4122),  -- Typically followed by
                                                  -- restriction data
   tow-away-zone                         (4123),
   school-zone                           (4124),  -- Treat as Speed Limit, with
                                                  -- details to follow
   speed-zone                            (4125),  -- Treat as Speed Limit, with
                                                  -- details to follow
   loading-zone                          (4126),  -- Typically followed by
                                                  -- restriction data
   state-law                             (4127),
   -- Cancel Types
   van-accessible                        (4128),
   special-parking-restrictions-lifted   (4222),
   no-parking-information-available      (4223)
   } (0..65535)


PavementConditions ::= INTEGER  {
   -- General
   impassable                     (5889),
   almost-impassable              (5890),
   passable-with-care             (5891),
   passable                       (5892),
   surface-water-hazard           (5893),
   danger-of-hydroplaning         (5894),
   wet-pavement                   (5895),
   treated-pavement               (5896),  -- Alternative Rendering: chemical wet
   slippery                       (5897),
   low-ground-clearance           (5938),  -- Use for W12-2 types
   at-grade-level-crossing        (5937),
   -- On Roadway items
   mud-on-roadway                 (5898),
   leaves-on-roadway              (5899),
   loose-sand-on-roadway          (5900),
   loose-gravel                   (5901),
   fuel-on-roadway                (5902),
   oil-on-roadway                 (5903),
   road-surface-in-poor-condition (5904),
   melting-tar                    (5905),
   uneven-lanes                   (5935),
   rough-road                     (5931),
   rough-crossing                 (5936),  -- Typically used with grade crossings at
                                           -- rails
   -- Ice & Snow
   ice                            (5906),
   icy-patches                    (5907),
   black-ice                      (5908),
   ice-pellets-on-roadway         (5909),
   ice-build-up                   (5910),
   freezing-rain                  (5911),
   wet-and-icy-roads              (5912),
   slush                          (5914),
   melting-snow                   (5913),
   frozen-slush                   (5915),
   snow-on-roadway                (5916),
   packed-snow                    (5917),
   packed-snow-patches            (5918),
   plowed-snow                    (5919),
   wet-snow                       (5920),
   fresh-snow                     (5921),
   powder-snow                    (5922),
   granular-snow                  (5923),
   frozen-snow                    (5924),
   crusted-snow                   (5925),
   deep-snow                      (5926),
   snow-drifts                    (5927),
   drifting-snow                  (5928),
   expected-snow-accumulation     (5929),
   current-snow-accumulation      (5930),
   -- Road Surface
   sand                           (5932),  -- Can use for W7-4d
   gravel                         (5933),  -- Can use for W7-4e
   paved                          (5934),  -- Can use for W7-4f
   -- Cancel Types
   dry-pavement                   (6011),
   snow-cleared                   (6012),
   pavement-conditions-improved   (6013),
   skid-hazard-reduced            (6014),
   pavement-conditions-cleared    (6015)
   } (0..65535)


Precipitation ::= INTEGER  {
   severe-weather           (4865),
   blizzard                 (4866),
   heavy-snow               (4867),
   snow                     (4868),
   light-snow               (4869),
   snow-showers             (4870),
   winter-storm             (4871),
   ice-glaze                (4872),
   heavy-frost              (4873),
   frost                    (4874),
   ice-storm                (4875),
   sleet                    (4876),
   rain-and-snow-mixed      (4877),
   rain-changing-to-snow    (4878),
   damaging-hail            (4879),
   hail                     (4880),
   thunderstorms            (4881),
   thundershowers           (4882),
   extremely-heavy-downpour (4883),
   heavy-rain               (4884),
   rain                     (4885),
   light-rain               (4886),
   drizzle                  (4887),
   showers                  (4888),
   dew                      (4889),
   -- Cancel Types
   precipitation-cleared    (4991)
   } (0..65535)


Qualifiers ::= INTEGER  {
   -- Locations
   above                     (7681),  -- Not to be used as the default for this category
   below                     (7682),
   in                        (7683),
   around                    (7684),
   after                     (7685),
   before                    (7686),
   at                        (7687),  -- Hint: used in conjunction with generic locations
   on                        (7688),  -- Hint: used in conjunction with "roadway" or
                                      -- other terms for both places (on-shoulder) and
                                      -- events (on-green)
   near                      (7689),  -- Hint: used with generic locations and lanes
   from-the                  (7690),
   terminal                  (7691),
   -- Weather Related
   falling-slowly            (7692),
   falling                   (7693),
   falling-quickly           (7694),
   rising-slowly             (7695),
   rising                    (7696),
   rising-quickly            (7697),
   steady                    (7698),
   likely                    (7699),
   changing-to               (7700),
   mostly                    (7701),
   partly                    (7702),
   minus                     (7703),
   weather-ended             (7704),
   expected                  (7705),
   low                       (7706),  -- Typically used in temperatures. See also "upper"
   mid                       (7707),
   high                      (7708),
   upper                     (7709),  -- Typically used in temperatures or broad regions.
                                      -- See also "low", "mid", "high", "middle"
   middle                    (7765),  -- Typically used for broad regions
                                      -- See also "upper", "lower"
   lower                     (7764),  -- Typically used for broad regions
                                      -- See also "upper", "middle"

   unseasonably              (7710),
   reported                  (7711),
   -- Instructions
   advice                    (7712),
   due-to                    (7713),
   proceed-to                (7714),
   transferred-to            (7715),
   use                       (7716),
   -- Prepositional Use
   affecting                 (7717),
   blocking                  (7718),
   connecting                (7719),
   finished                  (7720),  -- Alt term: finish
   for                       (7721),
   or                        (7722),
   -- Other
   and                       (7723),
   later                     (7724),
   level                     (7725),
   shortly                   (7726),
   soon                      (7727),
   service                   (7728),
   graffiti                  (7733),
   damaged                   (7729),
   out-of-order              (7730),  -- See Asset Status items as well
   on-State-right-of-way     (7732),
   found-property            (7734),
   vandalism                 (7731),
   major                     (7766),
   minor                     (7767),
   -- MUTCD Sign Usage
   begin-time                (7735),  -- Typically followed by a value entry and a
                                      -- time entry (AM/PM)
   added                     (7736),  -- Typically preceded by an object entry
   end-time                  (7737),  -- Typically followed by a value entry and a
                                      -- time entry (AM/PM)
   no                        (7738),  -- Typically followed by a value entry and
                                      -- any day/time limits
   do-not                    (7739),  -- Also used for "does not"
   block                     (7740),  -- Also used for blocks
   except                    (7741),  -- Typically followed by a value entry and a
                                      -- day/time entry
   day                       (7742),  -- Alt: daytime, daylight hours
   night                     (7743),  -- Alt: night time, night time hours
   any-time                  (7744),  -- Used also for "allowed"
   has                       (7745),  -- As in: has green (alt form: with)
   must                      (7757),  -- As in: <lane> must <turn>
   may-have                  (7746),  -- As in: may have green
   may-exceed                (7759),  -- As in: may exceed 80 mph
   only                      (7747),
   lifted                    (7748),  -- As in gate lifted
   empty                     (7749),
   turning                   (7750),  -- Used also for turns or turn
   u-turn                    (7751),  -- As in no u-turn allowed
   wait-for                  (7752),
   when-flashing             (7753),
   duration                  (7754),  -- Typically followed by a value entry and a
                                      -- time entry (Days/Hours/Min)
   cross                     (7755),
   when-wet                  (7756),
   oncoming                  (7758),  -- Typically followed by object or vehicle
                                      -- types
   to-request                (7760),  -- As in to request X do Y
   exempt                    (7761),
   skewed                    (7762),
   when-children-are-present (7763)   -- Use for S4-2
   } (0..65535)
   -- Modifiers and parts of sentences


RecreationalObjectsAndActivities ::= INTEGER  {
   -- General Items
   bear-viewing-area             (12033),  -- RG-020
   deer-viewing-area             (12034),  -- RG-040
   drinking-water                (12035),  -- RG-050
   environmental-study-area      (12036),  -- RG-060
   falling-rocks                 (12037),  -- RG-070 See also ITIS code: Rockfall
                                           -- 1309
   firearms                      (12038),  -- RG-080
   leashed-pets                  (12039),  -- RG-110
   point-of-interest             (12040),  -- RG-160
   smoking                       (12041),  -- RG-180
   dog                           (12042),  -- RG-240
   tent-camping                  (12043),  -- RM-010
   trailer-camping               (12044),  -- RM-020
   first-aid                     (12045),  -- RM-040
   handicapped                   (12046),  -- RM-080
   mechanic                      (12047),  -- RM-100
   trailer-sanitary-station      (12048),  -- RM-160  Alt: Trailer Waste Station
   viewing-area                  (12049),  -- RM-170
   scenic-overlook               (12095),  -- For D6-2
   campfire                      (12050),  -- RA-030
   locker                        (12051),  -- RA-070
   sleeping                      (12052),  -- RA-110 As in Sleeping Shelter
   trail                         (12053),  -- RA-120 As in Trail Shelter
   climbing                      (12054),  -- RL-020
   rock-climbing                 (12055),  -- RL-030
   hunting                       (12056),  -- RL-040
   playground                    (12057),  -- RL-050
   rock-collecting               (12058),  -- RL-060
   spelunking                    (12059),  -- RL-070
   bicycle-trail                 (12060),  -- RL-090
   hiking-trail                  (12061),  -- RL-100
   horse-trail                   (12062),  -- RL-110
   trail-interpretive-auto       (12063),  -- RL-120
   trail-interpretive-pedestrian (12064),  -- RL-130
   trail-road-for-4WD-vehicles   (12065),  -- RL-140
   trail-for-trail-bikes         (12066),  -- RL-150
   archer                        (12067),  -- RL-190
   hang-glider                   (12068),  -- RL-210
   -- Water Related
   boat-tours                    (12069),  -- RW-010
   canoeing                      (12070),  -- RW-020
   diving                        (12071),  -- RW-030
   scuba-diving                  (12072),  -- RW-040
   fishing                       (12073),  -- RW-050
   marine-recreation-area        (12074),  -- RW-060
   motorboating                  (12075),  -- RW-070
   boat-ramp                     (12076),  -- RW-080
   rowboating                    (12077),  -- RW-090
   sailboating                   (12078),  -- RW-100
   water-skiing                  (12079),  -- RW-110
   surfing                       (12080),  -- RW-120
   swimming                      (12081),  -- RW-130
   wading                        (12082),  -- RW-140
   hand-launch                   (12083),  -- RW-170
   kayak                         (12084),  -- RW-190
   wind-surf                     (12085),  -- RW-210
   -- Winter-Snow Related
   ice-skating                   (12086),  -- RS-010
   ski-jumping                   (12087),  -- RS-020
   bobbing                       (12088),  -- RS-030
   cross-country-skiing          (12089),  -- RS-040
   downhill-skiing               (12090),  -- RS-050
   sledding                      (12091),  -- RS-060
   snowmobiling                  (12092),  -- RS-070
   snowshoeing                   (12093),  -- RS-080
   winter-recreation-area        (12094)   -- RS-090
   } (0..65535)


RegulatoryAndWarningSigns ::= INTEGER  {
   -- MUTCD Signage Types
   regulatory-sign                       (12289),  -- Followed by sign data
   warning-sign                          (12290),  -- Followed by sign data
   information-sign                      (12291),  -- Followed by sign data
   construction-sign                     (12292),  -- Followed by sign data
   guide-sign                            (12293),  -- Followed by sign data
   -- MUCTD Basic Signs
   stop                                  (12294),
   yield                                 (12295),
   caution                               (12330),
   temporary                             (12331),
   to-oncoming-traffic                   (12296),
   four-way                              (12297),  -- As in 4-way stop
   all-way                               (12298),  -- All directions of travel
                                                   -- allowed or all lanes at a junction
   one-way                               (12329),  -- One direction of travel
                                                   -- allowed
   -- MUCTD Sign Fragments
   zone                                  (12299),  -- Typically preceded by type of
                                                   -- zone
   narrows                               (12300),  -- Used as an MUTCD sign,
                                                   -- typically preceded by road
   widens                                (12301),  -- Used as an MUTCD sign,
                                                   -- typically preceded by road
   reduced                               (12302),  -- Used as an MUTCD sign,
                                                   -- typically preceded by road or lane
   combined                              (12303),
   minimum                               (12304),
   maximum                               (12305),
   divided-road                          (12306),  -- Use for divided highway as
                                                   -- well
   double-arrow                          (12307),
   dead-end                              (12308),
   no-outlet                             (12309),
   wrong-way                             (12310),  -- R-5-1a
   do-not-enter                          (12314),  -- R-5-1
   nDetour                               (12312),  -- Typically followed by arrows
                                                   -- and distance
   chevron                               (12313),
   -- MUCTD Intersection Graphics
   t-intersection-to-the-side            (12315),
   t-intersection-oncoming               (12316),  -- Use for W2-4 graphic
   y-intersection-to-the-side            (12317),
   y-intersection-oncoming               (12318),  -- Use for W2-5 graphic
   four-way-divided-highway-crossing     (12319),  -- Use for R6-3 graphic
   t-way-divided-highway-crossing        (12320),  -- Use for R6-3a graphic
   light-rail-divided-highway-crossing   (12321),  -- Use for R15-7 graphic
   light-rail-t-divided-highway-crossing (12322),  -- Use for R15-7a graphic
   side-road-to-right                    (12323),  -- Use for W2-2R graphic
   side-road-to-left                     (12324),  -- Use for W2-2L graphic
   side-road-to-right-at-angle           (12325),  -- Use for W2-3R graphic
   side-road-to-left-at-angle            (12326),  -- Use for W2-3L graphic
   entering-roadway-merge                (12327),  -- Use for W4-5 graphic
   entering-roadway-added-lane           (12328)   -- Use for W4-6 graphic
   } (0..65535)


ResponderGroupAffected ::= INTEGER  {
   emergency-vehicle-units           (9729),  -- Default phrase, to be used when one of
                                              -- the below does not fit better
   federal-law-enforcement-units     (9730),
   state-police-units                (9731),
   county-police-units               (9732),  -- Hint: also sheriff response units
   local-police-units                (9733),
   ambulance-units                   (9734),
   rescue-units                      (9735),
   fire-units                        (9736),
   hAZMAT-units                      (9737),  -- Any vehicle assigned to HAZMAT duties
   light-tow-unit                    (9738),
   heavy-tow-unit                    (9739),
   private-tow-units                 (9743),  -- For 3rd Party tow trucks
   freeway-service-patrols           (9740),
   transportation-response-units     (9741),
   private-contractor-response-units (9742)
   } (0..65535)
   -- These groups are used in coordinated response and staging area information
   -- (rather than typically consumer related)


RestrictionClass ::= INTEGER  {
   restrictions                                     (2561),
   ramp-restrictions                                (2562),
   truck-restriction                                (2563),
   speed-restriction                                (2564),  -- Used for required speeds,
                                                             -- not advised speeds
   noise-restriction                                (2565),
   traffic-regulations-have-been-changed            (2566),
   local-access-only                                (2567),
   no-trailers                                      (2568),
   no-high-profile-vehicles                         (2569),
   hazardous-materials-truck-restriction            (2570),
   no-through-traffic                               (2571),
   no-motor-vehicles                                (2572),
   width-limit                                      (2573),  -- Typically followed by a
                                                             -- number and unit value
   height-limit                                     (2574),  -- Typically followed by a
                                                             -- number and unit value
   length-limit                                     (2575),  -- Typically followed by a
                                                             -- number and unit value
   axle-load-limit                                  (2576),  -- Typically followed by a
                                                             -- number and unit value
   gross-weight-limit                               (2577),  -- Typically followed by a
                                                             -- number and unit value
   axle-count-limit                                 (2578),  -- Typically followed by a
                                                             -- number and unit value
   carpool-lane-available                           (2579),
   carpool-restrictions-changed                     (2580),
   hOV-2-no-single-occupant-vehicles                (2581),
   hOV-3-no-vehicles-with-less-than-three-occupants (2582),
   bus-lane-available-for-all-vehicles              (2583),
   truck-lane-available-for-all-vehicles            (2584),
   permits-call-in-basis                            (2585),
   permits-temporarily-closed                       (2586),
   permits-closed                                   (2587),
   road-use-permits-required                        (2588),
   -- Cancel Types
   permits-open                                     (2675),
   restrictions-for-high-profile-vehicles-lifted    (2676),
   width-limit-lifted                               (2677),
   height-limit-lifted                              (2678),
   length-limit-lifted                              (2679),
   axle-load-limit-lifted                           (2680),
   weight-limit-lifted                              (2681),
   axle-count-limit-lifted                          (2682),
   carpool-restrictions-lifted                      (2683),
   lane-restrictions-lifted                         (2684),
   ramp-restrictions-lifted                         (2685),
   motor-vehicle-restrictions-lifted                (2686),
   restrictions-lifted                              (2687)
   } (0..65535)


RoadsideAssets ::= INTEGER  {
   -- Inanimate Objects
   none                        (10496),  -- Implies free text follows
   light-pole                  (10497),
   utility-pole                (10498),
   gantry-way                  (10499),
   sign-support                (10500),  -- All forms of signage
   signal-pole                 (10501),
   signage-public              (10502),
   signage-private             (10503),
   overhead-sign               (10568),
   ground-sign                 (10569),
   cones                       (10504),  -- Typical std height cones as per MUTCD
   cones-post-type             (10505),  -- Also called channelizer cones or delineator
                                         -- posts
   cones-glue-post             (10506),  -- For all glue-down types
   cones-other                 (10507),  -- Specialty types or misc. smaller cones
   barriers                    (10508),
   barrier-Aframe              (10509),  -- Sizes larger than 1.5 meters in length
   barriers-heavy-duty         (10510),  -- All types requiring equipment to place
   barricade-type-III          (10511),  -- All collapsible Type III Barricades
   barricade-small             (10512),  -- Type I and all small A frame types, also
                                         -- so-called "mini" or "narrows" types
   solid-barrier               (10565),
   moveable-barrier            (10566),
   barricade-lights            (10513),  -- Std 7" light as per ITE stds
   beacon                      (10514),  -- All types of strobe and rotating lights
   t-stand                     (10515),
   a-stand                     (10516),
   drums                       (10517),  -- Common drums and barrel types
   sand-barrel                 (10567),
   impact-attenuator           (10518),  -- Water-filled and other crushable types
   barricade-tape              (10519),  -- Lettering type (legend) to be conveyed
                                         -- elsewhere
   safety-fence                (10520),
   temp-pavement-markings      (10521),  -- All forms of temp markings
   speed-bumps                 (10522),  -- Use also for speed humps
   temp-curbs                  (10523),
   parking-blocks              (10524),
   signboard-fixed             (10525),
   signboard-portable          (10526),
   stripe                      (10572),
   island                      (10573),  -- Used for raised islands in median
   -- Controllable or Active Objects
   har                         (10527),  -- Transmission type not known
   har-AM                      (10528),
   har-FM                      (10529),
   har-DSRC                    (10530),
   traffic-light               (10531),  -- Also used for signalized intersections
   lane-control-signal         (10532),
   traffic-detector            (10533),
   vehicle-detector            (10534),
   system-alarm                (10535),
   arrow-board                 (10536),
   fixed-VMS                   (10537),
   mobile-VMS                  (10538),
   ramp-control                (10539),
   gate-control                (10540),  -- Other than rail types
   temporary-traffic-light     (10541),
   over-height-warning-system  (10542),
   over-weight-warning-system  (10543),
   emergency-telephones        (10544),
   railroad-crossing-equipment (10545),
   tunnel-ventilation          (10546),  -- Use also for fans
   ccTV                        (10547),
   environmental-sensor        (10548),
   emergency-signal            (10570),
   countdown-pedestrian-sign   (10571),
   -- Items Used by Rail and Transit
   switch                      (10549),  -- In the context of a railroad device
   signal                      (10550),  -- In the context of a railroad device
   third-rail                  (10551),
   overhead-power              (10552),  -- Specifically the power feed line for a
                                         -- vehicle, do not use for general power lines
   concrete-tie                (10553),
   wooden-tie                  (10554),
   manhole-cover               (10559),
   -- Misc. Items
   culvert                     (10560),
   escalator                   (10555),
   elevator                    (10556),
   snow-poles                  (10561),  -- A tall pole and overhanging arm (like a
                                         -- luminaire) with reflective markers to help
                                         -- indicate roadway in mountain passes during
                                         -- whiteout conditions
   track                       (10557),
   guide-poles                 (10562),  -- Poles along road to indicate guard rail in
                                         -- deep snow
   drawbridge                  (10558),
   expansion-joint             (10563),
   shifted-plate               (10564)
   } (0..65535)


Roadwork ::= INTEGER  {
   -- Roads
   road-construction                          (1025),  -- Alt text: Road Work
   major-road-construction                    (1026),
   long-term-road-construction                (1027),
   construction-work                          (1028),
   paving-operations                          (1029),
   work-in-the-median                         (1030),
   road-reconstruction                        (1031),
   opposing-traffic                           (1032),
   narrow-lanes                               (1033),
   construction-traffic-merging               (1034),
   single-line-traffic-alternating-directions (1035),
   road-maintenance-operations                (1036),
   road-marking-operations                    (1037),
   road-widening                              (1061),  -- Used for roadwork, not as an
                                                       -- MUTCD sign
   cracks                                     (1052),  -- Used for disjoint roadway
                                                       -- surface
   crack-REMOVE                               (1058),  -- No Longer Used. Used for
                                                       -- disjoint roadway surface
   bumps                                      (1053),  -- Used for swelling
   drop-off                                   (1059),
   storm-drain                                (1054),
   -- Bridges
   bridge-maintenance-operations              (1038),
   bridge-construction                        (1039),
   bridge-demolition-work                     (1040),
   seismic-retrofit                           (1060),  -- All types of earthquake
                                                       -- construction
   -- Other
   overgrown-grass                            (1055),
   overgrown-brushshrubs                      (1056),
   overgrown-trees                            (1057),
   blasting                                   (1041),  -- See also: avalanche
   avalanche-control-activities               (1042),
   water-main-work                            (1043),
   gas-main-work                              (1044),
   work-on-underground-cables                 (1045),
   work-on-underground-services               (1046),
   new-road-construction-layout               (1047),
   new-road-layout                            (1048),
   temporary-lane-markings                    (1049),
   temporary-traffic-lights                   (1050),
   emergency-maintenance                      (1051),
   utility-work                               (1062),
   -- Cancel Types
   road-maintenance-cleared                   (1146),
   normal-road-layout-restored                (1147),
   road-work-clearance-in-progress            (1148),
   road-construction-cleared                  (1149),
   normal-traffic-lanes-restored              (1150),
   road-work-cleared                          (1151)
   } (0..65535)


SmallNumbers ::= INTEGER  {
   n1   (12545),
   n2   (12546),
   n3   (12547),
   n4   (12548),
   n5   (12549),
   n6   (12550),
   n7   (12551),
   n8   (12552),
   n9   (12553),
   n10  (12554),
   n11  (12555),
   n12  (12556),
   n13  (12557),
   n14  (12558),
   n15  (12559),
   n16  (12560),
   n17  (12561),
   n18  (12562),
   n19  (12563),
   n20  (12564),
   n21  (12565),
   n22  (12566),
   n23  (12567),
   n24  (12568),
   n25  (12569),
   n26  (12570),
   n27  (12571),
   n28  (12572),
   n29  (12573),
   n30  (12574),
   n31  (12575),
   n32  (12576),
   n33  (12577),
   n34  (12578),
   n35  (12579),
   n36  (12580),
   n37  (12581),
   n38  (12582),
   n39  (12583),
   n40  (12584),
   n41  (12585),
   n42  (12586),
   n43  (12587),
   n44  (12588),
   n45  (12589),
   n46  (12590),
   n47  (12591),
   n48  (12592),
   n49  (12593),
   n50  (12594),
   n51  (12595),
   n52  (12596),
   n53  (12597),
   n54  (12598),
   n55  (12599),
   n56  (12600),
   n57  (12601),
   n58  (12602),
   n59  (12603),
   n60  (12604),
   n61  (12605),
   n62  (12606),
   n63  (12607),
   n64  (12608),
   n65  (12609),
   n66  (12610),
   n67  (12611),
   n68  (12612),
   n69  (12613),
   n70  (12614),
   n71  (12615),
   n72  (12616),
   n73  (12617),
   n74  (12618),
   n75  (12619),
   n76  (12620),
   n77  (12621),
   n78  (12622),
   n79  (12623),
   n80  (12624),
   n81  (12625),
   n82  (12626),
   n83  (12627),
   n84  (12628),
   n85  (12629),
   n86  (12630),
   n87  (12631),
   n88  (12632),
   n89  (12633),
   n90  (12634),
   n91  (12635),
   n92  (12636),
   n93  (12637),
   n94  (12638),
   n95  (12639),
   n96  (12640),
   n97  (12641),
   n98  (12642),
   n99  (12643),
   n100 (12644),
   n101 (12645),
   n102 (12646),
   n103 (12647),
   n104 (12648),
   n105 (12649),
   n106 (12650),
   n107 (12651),
   n108 (12652),
   n109 (12653),
   n110 (12654),
   n111 (12655),
   n112 (12656),
   n113 (12657),
   n114 (12658),
   n115 (12659),
   n116 (12660),
   n117 (12661),
   n118 (12662),
   n119 (12663),
   n120 (12664),
   n121 (12665),
   n122 (12666),
   n123 (12667),
   n124 (12668),
   n125 (12669),
   n126 (12670),
   n127 (12671),
   n128 (12672),
   n129 (12673),
   n130 (12674),
   n131 (12675),
   n132 (12676),
   n133 (12677),
   n134 (12678),
   n135 (12679),
   n136 (12680),
   n137 (12681),
   n138 (12682),
   n139 (12683),
   n140 (12684),
   n141 (12685),
   n142 (12686),
   n143 (12687),
   n144 (12688),
   n145 (12689),
   n146 (12690),
   n147 (12691),
   n148 (12692),
   n149 (12693),
   n150 (12694),
   n151 (12695),
   n152 (12696),
   n153 (12697),
   n154 (12698),
   n155 (12699),
   n156 (12700),
   n157 (12701),
   n158 (12702),
   n159 (12703),
   n160 (12704),
   n161 (12705),
   n162 (12706),
   n163 (12707),
   n164 (12708),
   n165 (12709),
   n166 (12710),
   n167 (12711),
   n168 (12712),
   n169 (12713),
   n170 (12714),
   n171 (12715),
   n172 (12716),
   n173 (12717),
   n174 (12718),
   n175 (12719),
   n176 (12720),
   n177 (12721),
   n178 (12722),
   n179 (12723),
   n180 (12724),
   n181 (12725),
   n182 (12726),
   n183 (12727),
   n184 (12728),
   n185 (12729),
   n186 (12730),
   n187 (12731),
   n188 (12732),
   n189 (12733),
   n190 (12734),
   n191 (12735),
   n192 (12736),
   n193 (12737),
   n194 (12738),
   n195 (12739),
   n196 (12740),
   n197 (12741),
   n198 (12742),
   n199 (12743),
   n200 (12744),
   n201 (12745),
   n202 (12746),
   n203 (12747),
   n204 (12748),
   n205 (12749),
   n206 (12750),
   n207 (12751),
   n208 (12752),
   n209 (12753),
   n210 (12754),
   n211 (12755),
   n212 (12756),
   n213 (12757),
   n214 (12758),
   n215 (12759),
   n216 (12760),
   n217 (12761),
   n218 (12762),
   n219 (12763),
   n220 (12764),
   n221 (12765),
   n222 (12766),
   n223 (12767),
   n224 (12768),
   n225 (12769),
   n226 (12770),
   n227 (12771),
   n228 (12772),
   n229 (12773),
   n230 (12774),
   n231 (12775),
   n232 (12776),
   n233 (12777),
   n234 (12778),
   n235 (12779),
   n236 (12780),
   n237 (12781),
   n238 (12782),
   n239 (12783),
   n240 (12784),
   n241 (12785),
   n242 (12786),
   n243 (12787),
   n244 (12788),
   n245 (12789),
   n246 (12790),
   n247 (12791),
   n248 (12792),
   n249 (12793),
   n250 (12794),
   n251 (12795),
   n252 (12796),
   n253 (12797),
   n254 (12798),
   n255 (12799)
   } (0..65535)


SpecialEvents ::= INTEGER  {
   major-event            (3841),
   airshow                (3842),
   hot-air-ballooning     (3843),
   concert                (3844),
   state-occasion         (3845),
   vIP-visit              (3846),
   show                   (3847),
   festival               (3848),  -- Used for farmers' markets as well
   exhibition             (3849),
   performing-arts        (3850),
   outdoor-market         (3851),  -- Used for farmers' markets as well
   fair                   (3852),
   carnival               (3853),
   fireworks-display      (3854),
   trade-expo             (3855),
   movie-filming          (3856),
   presidential-visit     (3857),
   parade                 (3858),
   procession             (3859),
   funeral-procession     (3860),
   crowd                  (3861),
   holiday-traffic-crowds (3862),
   -- Cancel Types
   event-ended            (3967)
   } (0..65535)
   -- Events which affect the local roads


SportingEvents ::= INTEGER  {
   sports-event          (3585),
   game                  (3586),
   tournament            (3587),
   track-and-field-event (3588),
   baseball-game         (3589),
   basketball-game       (3590),
   boxing-match          (3591),
   football-game         (3592),
   soccer-game           (3593),
   golf-tournament       (3594),
   hockey-game           (3595),
   tennis-tournament     (3596),
   wrestling-match       (3597),
   road-race             (3598),  -- Hint: used for motorcycle races as well
   automobile-race       (3599),
   bicycle-race          (3600),
   race-event            (3601),
   marathon              (3602),
   horse-show            (3603),
   rodeo                 (3604),
   water-sports-event    (3605),
   winter-sports-event   (3606),
   skating-event         (3607),
   dog-sled-race         (3608),
   -- Cancel Types
   sporting-event-ended  (3711)
   } (0..65535)
   -- Events occurring on or nearby the roadway


StatesAndTerritories ::= INTEGER  {
   alabama                   (12801),
   alaska                    (12802),
   american-Samoa            (12803),
   arizona                   (12804),
   arkansas                  (12805),
   california                (12806),
   colorado                  (12807),
   connecticut               (12808),
   delaware                  (12809),
   district-of-Columbia      (12810),
   florida                   (12811),
   georgia                   (12812),
   guam                      (12813),
   hawaii                    (12814),
   idaho                     (12815),
   illinois                  (12816),
   indiana                   (12817),
   iowa                      (12818),
   kansas                    (12819),
   kentucky                  (12820),
   louisiana                 (12821),
   maine                     (12822),
   maryland                  (12823),
   massachusetts             (12824),
   michigan                  (12825),
   minnesota                 (12826),
   mississippi               (12827),
   missouri                  (12828),
   montana                   (12829),
   nebraska                  (12830),
   nevada                    (12831),
   new-Hampshire             (12832),
   new-Jersey                (12833),
   new-Mexico                (12834),
   new-York                  (12835),
   north-Carolina            (12836),
   north-Dakota              (12837),
   northern-Marianas-Islands (12838),
   ohio                      (12839),
   oklahoma                  (12840),
   oregon                    (12841),
   pennsylvania              (12842),
   puerto-rico               (12843),
   rhode-Island              (12844),
   south-Carolina            (12845),
   south-Dakota              (12846),
   tennessee                 (12847),
   texas                     (12848),
   utah                      (12849),
   vermont                   (12850),
   virginia                  (12851),
   virgin-Islands            (12852),
   washington                (12853),
   west-Virginia             (12854),
   wisconsin                 (12855),
   wyoming                   (12856)
   } (0..65535)


StreetSuffixes ::= INTEGER  {
   alley      (13313),
   annex      (13314),
   arcade     (13315),
   avenue     (13316),
   bayoo      (13317),
   beach      (13318),
   bend       (13319),
   bluff      (13320),
   bottom     (13321),
   boulevard  (13322),
   branch     (13323),
   nBridge    (13324),  -- Note use of "n" to avoid conflict with other entry
   brook      (13325),
   burg       (13326),
   bypass     (13327),
   camp       (13328),
   canyon     (13329),
   cape       (13330),
   causeway   (13331),
   nCenter    (13332),  -- Note use of "n" to avoid conflict with other entry
   circle     (13333),
   cliff      (13334),
   club       (13335),
   common     (13336),
   corner     (13337),
   course     (13338),
   court      (13339),
   cove       (13340),
   creek      (13341),
   crescent   (13342),
   crest      (13343),
   nCrossing  (13344),  -- Note use of "n" to avoid conflict with other entry
   crossroad  (13345),
   curve      (13346),
   dale       (13347),
   nDam       (13348),  -- Note use of "n" to avoid conflict with other entry
   divide     (13349),
   drive      (13350),
   estate     (13351),
   expressway (13352),
   extension  (13353),
   fall       (13354),
   nFerry     (13355),  -- Note use of "n" to avoid conflict with other entry
   field      (13356),
   flat       (13357),
   ford       (13358),
   forest     (13359),
   forge      (13360),
   fork       (13361),
   fort       (13362),
   nFreeway   (13363),  -- Note use of "n" to avoid conflict with other entry
   garden     (13364),
   gateway    (13365),
   glen       (13366),
   green      (13367),
   grove      (13368),
   harbor     (13369),
   haven      (13370),
   heights    (13371),
   highway    (13372),
   nHill      (13373),  -- Note use of "n" to avoid conflict with other entry
   hollow     (13374),
   inlet      (13375),
   nIsland    (13376),  -- Note use of "n" to avoid conflict with other entry
   isle       (13377),
   nJunction  (13378),  -- Note use of "n" to avoid conflict with other entry
   key        (13379),
   knoll      (13380),
   lake       (13381),
   land       (13382),
   landing    (13383),
   nLane      (13384),  -- Note use of "n" to avoid conflict with other entry
   light      (13385),
   loaf       (13386),
   lock       (13387),
   lodge      (13388),
   loop       (13389),
   mall       (13390),
   manor      (13391),
   meadow     (13392),
   mews       (13393),
   mill       (13394),
   mission    (13395),
   motorway   (13396),
   mount      (13397),
   mountain   (13398),
   neck       (13399),
   orchard    (13400),
   oval       (13401),
   nOverpass  (13402),  -- Note use of "n" to avoid conflict with other entry
   park       (13403),
   parkway    (13404),
   nPass      (13405),  -- Note use of "n" to avoid conflict with other entry
   passage    (13406),
   path       (13407),
   pike       (13408),
   pine       (13409),
   plains     (13410),
   plaza      (13411),
   point      (13412),
   port       (13413),
   prairie    (13414),
   radial     (13415),
   ramp       (13416),
   ranch      (13417),
   rapid      (13418),
   rest       (13419),
   ridge      (13420),
   river      (13421),
   nRoad      (13422),  -- Note use of "n" to avoid conflict with other entry
   route      (13423),
   row        (13424),
   rue        (13425),
   run        (13426),
   shoal      (13427),
   shore      (13428),
   skyway     (13429),
   spring     (13430),
   nSpur      (13431),  -- Note use of "n" to avoid conflict with other entry
   square     (13432),
   nStation   (13433),  -- Note use of "n" to avoid conflict with other entry
   stravenue  (13434),
   stream     (13435),
   street     (13436),
   summit     (13437),
   terrace    (13438),
   throughway (13439),
   trace      (13440),
   nTrack     (13441),  -- Note use of "n" to avoid conflict with other entry
   trafficway (13442),
   nTrail     (13443),  -- Note use of "n" to avoid conflict with other entry
   nTunnel    (13444),  -- Note use of "n" to avoid conflict with other entry
   turnpike   (13445),
   nUnderpass (13446),  -- Note use of "n" to avoid conflict with other entry
   union      (13447),
   valley     (13448),
   viaduct    (13449),
   view       (13450),
   village    (13451),
   ville      (13452),
   vista      (13453),
   nWalk      (13454),  -- Note use of "n" to avoid conflict with other  entry
   wall       (13455),
   way        (13456),
   well       (13457)
   } (0..65535)


Structures ::= INTEGER  {
   rest-room                       (13057),  -- RM-140
   mens-rest-room                  (13058),  -- RA-090
   womens-rest-room                (13059),  -- RA-100
   family-rest-room                (13060),  -- RA-150
   dam                             (13061),  -- RG-030
   fish-hatchery                   (13062),  -- RG-090
   information                     (13063),  -- RG-100
   lighthouse                      (13064),  -- RG-120
   lookout-tower                   (13065),  -- RG-140
   ranger-station                  (13066),  -- RG-170
   grocery-store                   (13068),  -- RM-070
   lodging                         (13069),  -- RM-090
   post-office                     (13070),  -- RM-110
   picnic-shelter                  (13072),  -- RM-130
   group-camping                   (13073),  -- RM-210
   group-picnicking                (13074),  -- RM-220
   n24-hour-pharmacy               (13075),  -- RM-230
   kennel                          (13076),  -- RA-050
   laundry-facilities              (13077),  -- RA-060
   shower-facilities               (13078),  -- RA-130
   amphitheater                    (13079),  -- RL-010
   stable                          (13080),  -- RL-080
   hospital                        (13081),  -- D9-13a or D9-2
   emergency-medical-service-point (13082),  -- Use for emergency medical care as
                                             -- well D9-13c
   library                         (13083),  -- I-8p
   recycling-collection-center     (13084),  -- I-11
   school                          (13085)   -- Use for S1-1
   } (0..65535)


SuggestionAdvice ::= INTEGER  {
   why-not-ride-share                         (6657),
   is-this-your-no-ride-day                   (6658),
   why-not-use-transit                        (6659),
   why-not-park-and-ride                      (6660),
   why-not-try-paratransit                    (6661),
   why-not-travel-by-rail                     (6662),
   why-not-use-the-subway                     (6663),
   why-not-try-rapid-transit                  (6664),
   why-not-travel-by-bus                      (6665),
   your-parking-ticket-covers-the-return-ride (6666),
   avoid-the-rush-hour                        (6667),
   do-not-allow-unnecessary-gaps              (6668),
   follow-the-vehicle-in-front-smoothly       (6669),
   do-not-slow-down-unnecessarily             (6670),
   watch-for-muggers                          (6671),
   watch-for-pickpockets                      (6672),
   watch-for-thieves                          (6673),
   sorry-for-any-delay                        (6674),
   thank-you-for-your-understanding           (6675),
   we-appreciate-your-patience                (6676),
   we-are-grateful-for-your-cooperation       (6677),
   share-the-road                             (6678)
   } (0..65535)


Temperature ::= INTEGER  {
   maximum-temperature                     (5633),  -- This index is not to be used as a
                                                    -- default value for this category
   temperature                             (5634),  -- Typically followed by a number
                                                    -- value and a unit value
   minimum-temperature                     (5635),
   current-temperature                     (5636),
   heat-index                              (5637),
   extreme-heat                            (5638),
   hot                                     (5639),
   hotter                                  (5640),
   heat                                    (5641),
   warmer                                  (5642),
   warm                                    (5643),
   mild                                    (5644),
   cool                                    (5645),
   cooler                                  (5646),
   cold                                    (5647),
   colder                                  (5648),
   very-cold                               (5649),
   extreme-cold                            (5650),
   wind-chill                              (5651),
   dewpoint                                (5652),
   relative-humidity                       (5653),
   -- Cancel Types
   temperatures-close-to-the-seasonal-norm (5758),
   less-extreme-temperatures               (5759)
   } (0..65535)


TrafficConditions ::= INTEGER  {
   stopped-traffic                  (257),
   stop-and-go-traffic              (258),
   slow-traffic                     (259),
   heavy-traffic                    (260),
   traffic-building                 (261),
   long-queues                      (262),
   traffic-congestion               (263),
   traffic-lighter-than-normal      (264),
   traffic-heavier-than-normal      (265),
   traffic-much-heavier-than-normal (266),
   current-speed                    (267),  -- Typically followed by a value entry and a
                                            -- units entry (MPH/KPH)
   speed-limit                      (268),  -- Typically followed by a value entry and a
                                            -- units entry (MPH/KPH)
   travel-time                      (269),  -- Typically followed by a value entry and a
                                            -- units entry (seconds)
   merging-traffic                  (272),  -- Typically followed by direction
                                            -- left/right. Can be used for W4-1R and
                                            -- W4-1L signs
   contraflow                       (273),
   -- Cancel Types
   contraflow-canceled              (378),
   traffic-flowing-freely           (379),
   traffic-easing                   (380),  -- Alternative rendering: traffic clearing
   traffic-returned-to-normal       (381),
   no-problems-to-report            (382),
   traffic-congestion-cleared       (383)
   } (0..65535)


TransitMode ::= INTEGER  {
   travel             (8961),  -- Hint: may include all modes
   transit            (8962),  -- Hint: may include all public transit modes
   bus                (8963),
   trolleybus         (8964),
   rail               (8965),
   commuter-rail      (8966),
   subway             (8967),
   rapid-transit      (8968),
   light-rail         (8969),
   streetcar          (8970),  -- Alternative Rendering: tram
   dial-a-ride        (8971),  -- Alternative Rendering: demand responsive transit
   park-and-ride      (8972),  -- Not to be used as a place
   shuttle            (8973),
   free-shuttle       (8974),  -- Alternative Rendering: tram
   airport-shuttle    (8975),
   taxies             (8976),
   ferry              (8977),
   passenger-ferry    (8978),
   vehicle-ferry      (8979),
   aerial-tramway     (8980),
   automated-guideway (8981),  -- Include all types of guideways
   cable-cars         (8982),
   monorail           (8983),
   air-travel         (8984),  -- All modes of air travel
   hitch-hitching     (8985),
   walk               (8986)   -- Alt form: Walking
   } (0..65535)
   -- Used to describe various types of transit services, and information pertaining
   -- to the whole mode. If you wish to identify a specific vehicle (such as a bus not
   -- the bus fleet), use Vehicle Group


TransitOperations ::= INTEGER  {
   unknown-transit-problem                       (10753),
   sleeping-customer                             (10754),
   assault-on-passenger                          (10755),
   assault-on-employee                           (10756),
   broken-seat                                   (10757),
   bus-alarm                                     (10758),
   crime-or-drug-deal                            (10759),
   eating-on-board                               (10760),
   equipment-problem-with-air-conditioning       (10761),
   equipment-problem-with-air-system             (10762),
   equipment-problem-with-brakes                 (10763),
   equipment-problem-with-chassis-or-suspension  (10764),
   equipment-problem-with-cooling-system         (10765),
   equipment-problem-with-doors                  (10766),
   equipment-problem-with-electrical             (10767),
   equipment-problem-with-engine                 (10768),
   equipment-problem-with-exterior-or-body       (10769),
   equipment-problem-with-fare-collection        (10770),
   equipment-problem-with-fuel-or-exhaust        (10771),
   equipment-problem-with-horn                   (10772),
   equipment-problem-with-interior               (10773),
   equipment-problem-with-liftkneeling           (10774),
   equipment-problem-with-lights                 (10775),
   equipment-problem-with-lubrication            (10776),
   equipment-problem-with-radio-or-communication (10777),
   equipment-problem-with-signs                  (10778),
   equipment-problem-with-steering               (10779),
   equipment-problem-with-tires                  (10780),
   equipment-problem-with-transmission           (10781),
   equipment-problem-with-unknown-alarm          (10782),
   equipment-problem-with-wipers                 (10783),
   fare-dispute-expired-pass                     (10784),
   fare-dispute-expired-transfer                 (10785),
   fare-dispute-expired-upgrade                  (10786),
   fare-dispute-other                            (10787),
   fare-dispute-refuses-to-pay                   (10788),
   lift-passenger-cycle-completed                (10789),
   lift-passenger-ready-to-alight                (10790),
   lift-passenger-ready-to-board                 (10791),
   lost-article                                  (10792),
   objects-thrown                                (10793),
   passenger-accident-alighting                  (10794),
   passenger-accident-boarding                   (10795),
   passenger-accident-fallen-on-board            (10796),
   passenger-load                                (10797),
   passenger-accident-other                      (10798),
   passenger-sick-or-injured                     (10799),
   right-of-way                                  (10800),
   theft                                         (10801),
   theft-of-service                              (10802),
   waiting-to-get-relief-for-schedule-break      (10803),
   waiting-to-get-relief-after-run-is-finished   (10804),
   waiting-to-provide-relief                     (10805)
   } (0..65535)


TravelerGroupAffected ::= INTEGER  {
   through-traffic                 (9473),
   holiday-traffic                 (9474),
   residents                       (9475),
   visitors                        (9476),
   long-distance-traffic           (9477),
   local-traffic                   (9478),
   regional-traffic                (9479),
   arrivals                        (9480),
   departures                      (9481),
   airline-travelers               (9482),
   commuter-airline-travelers      (9483),
   domestic-airline-travelers      (9484),
   international-airline-travelers (9485),
   pedestrians                     (9486),
   bicyclists                      (9487)   -- Hint: may be used as a traveler
                                            -- restriction, as in "bicycles prohibited on
                                            -- subways during rush hour" or "road closed
                                            -- to bicyclists"
   } (0..65535)


Units ::= INTEGER  {
   -- Areas,  Distances  &  Speeds
   square-feet             (8705),
   square-meters           (8706),
   acres                   (8707),
   hectares                (8708),
   inches                  (8709),
   feet                    (8710),
   mile                    (8711),  -- Hint: used for offset as in "at mile 123"
                                    -- Alternative Rendering: milepost marker
   miles                   (8712),  -- Hint: Used for distance, as in "ending 5 miles"
   nautical-miles          (8713),
   millimeters             (8714),
   meters                  (8715),
   kilometer               (8716),  -- Hint: used for offset as in "at kilometer 123"
   kilometers              (8717),
   feet-per-second         (8718),
   meters-per-second       (8719),
   mPH                     (8720),
   kPH                     (8721),
   knots                   (8722),
   elevation               (8766),  -- Typically followed by value and units
   -- Times,  Days  &  Dates
   aM                      (8723),  -- Both a time value and a radio band value. A
                                    -- number value may PRECEDE the unit value used in
                                    -- representing the frequency of a radio station
   pM                      (8724),
   holiday                 (8726),
   seconds                 (8727),
   minutes                 (8728),
   hours                   (8729),
   days                    (8730),  -- Hint: useful for events occurring for at least 24
                                    -- hours
   weeks                   (8731),
   months                  (8732),
   other-times             (8767),  -- Typically used to represent a "default"
                                    -- allowed condition
   -- Days of the Week
   nSunday                 (8758),
   nMonday                 (8759),
   nTuesday                (8760),
   nWednesday              (8761),
   nThursday               (8762),
   nFriday                 (8763),
   nSaturday               (8764),
   weekdays                (8765),  -- Alt text: Mon-Fri
   weekends                (8725),  -- In general date/time values can be better coded in
                                    -- other ways in most message sets
   -- Temps, Weights, Masses and Measurements
   degrees-Angle           (8733),  -- Used for latitude, longitude and bearing measured
                                    -- clockwise from North
   degrees-Celsius         (8734),  -- Alternate renderings possible
   degrees-Fahrenheit      (8735),  -- Alternate renderings possible
   grams                   (8736),
   kilograms               (8737),  -- Also called a metric ton (1000kg or ~2204 lbs)
   ounces                  (8738),
   pounds                  (8739),
   tons                    (8740),  -- English Units (2000 lbs = 1 ton)
   fluid-ounces            (8741),
   gallons                 (8742),
   milliliters             (8743),
   liters                  (8744),
   kilograms-per-lane-mile (8745),
   tons-per-lane-mile      (8746),
   -- Misc.
   dollar                  (8747),  -- Alternative rendering: dollar symbol  Not to be
                                    -- used as the default value for this category
   percent                 (8748),  -- Alternative rendering: percent symbol
   grade                   (8757),  -- Typically preceded by a percent value entry
   time-delimiter          (8749),  -- Alternative rendering: "-"
   dollars                 (8750),  -- Alternative rendering can use local currency sign
   flight-number           (8751),  -- A number value may PRECEDE the unit value in use
   person-people           (8752),
   response-plan           (8753),  -- A value may PRECEDE the unit value in use
                                    -- (involving a combination of numbers and/or
                                    -- letters)
   placard-type            (8754),  -- For hazmat class and division type designations, a
                                    -- value may PRECEDE the unit value in use
   placard-number          (8755),  -- For chemical designations, a value may PRECEDE the
                                    -- unit value in use
   fM                      (8756)   -- A number value may PRECEDE the unit value in use
                                    -- representing the frequency of a radio station
   } (0..65535)
   -- Used in conjunction with # values. In many ITS messages there are specific
   -- place holders (data elements) in the message set to send these values. This
   -- category shall not be used to circumvent message sets which support various units
   -- in this way


UnusualDriving ::= INTEGER  {
   vehicle-traveling-wrong-way       (1793),
   reckless-driver                   (1794),  -- Alternative Rendering: erratic driver
   prohibited-vehicle-on-roadway     (1795),
   emergency-vehicles-on-roadway     (1796),
   high-speed-emergency-vehicles     (1797),
   high-speed-chase                  (1798),
   -- Cancel Types
   dangerous-vehicle-warning-cleared (1918),
   emergency-vehicle-warning-cleared (1919)
   } (0..65535)


ValidManeuvers ::= INTEGER  {
   prohibit-None-Allowed-LU-LT-L45-S-R45-RT-RU (11264),
   prohibit-RU-Allowed-LU-LT-L45-S-R45-RT      (11265),  -- All Maneuvers allowed
   prohibit-RT-Allowed-LU-LT-L45-S-R45-RU      (11266),
   prohibit-RT-RU-Allowed-LU-LT-L45-S-R45      (11267),
   prohibit-R45-Allowed-LU-LT-L45-S-RT-RU      (11268),
   prohibit-R45-RU-Allowed-LU-LT-L45-S-RT      (11269),
   prohibit-R45-RT-Allowed-LU-LT-L45-S-RU      (11270),
   prohibit-R45-RT-RU-Allowed-LU-LT-L45-S      (11271),  -- Left or Straight Only
                                                         -- (R3-6), Right Turn prohibited
   prohibit-S-Allowed-LU-LT-L45-R45-RT-RU      (11272),
   prohibit-S-RU-Allowed-LU-LT-L45-R45-RT      (11273),
   prohibit-S-RT-Allowed-LU-LT-L45-R45-RU      (11274),
   prohibit-S-RT-RU-Allowed-LU-LT-L45-R45      (11275),
   prohibit-S-R45-Allowed-LU-LT-L45-RT-RU      (11276),
   prohibit-S-R45-RU-Allowed-LU-LT-L45-RT      (11277),
   prohibit-S-R45-RT-Allowed-LU-LT-L45-RU      (11278),
   prohibit-S-R45-RT-RU-Allowed-LU-LT-L45      (11279),
   prohibit-L45-Allowed-LU-LT-S-R45-RT-RU      (11280),  -- Left 45 deg turn
                                                         -- prohibited
   prohibit-L45-RU-Allowed-LU-LT-S-R45-RT      (11281),
   prohibit-L45-RT-Allowed-LU-LT-S-R45-RU      (11282),
   prohibit-L45-RT-RU-Allowed-LU-LT-S-R45      (11283),
   prohibit-L45-R45-Allowed-LU-LT-S-RT-RU      (11284),
   prohibit-L45-R45-RU-Allowed-LU-LT-S-RT      (11285),
   prohibit-L45-R45-RT-Allowed-LU-LT-S-RU      (11286),
   prohibit-L45-R45-RT-RU-Allowed-LU-LT-S      (11287),
   prohibit-L45-S-Allowed-LU-LT-R45-RT-RU      (11288),
   prohibit-L45-S-RU-Allowed-LU-LT-R45-RT      (11289),
   prohibit-L45-S-RT-Allowed-LU-LT-R45-RU      (11290),
   prohibit-L45-S-RT-RU-Allowed-LU-LT-R45      (11291),
   prohibit-L45-S-R45-Allowed-LU-LT-RT-RU      (11292),
   prohibit-L45-S-R45-RU-Allowed-LU-LT-RT      (11293),
   prohibit-L45-S-R45-RT-Allowed-LU-LT-RU      (11294),
   prohibit-L45-S-R45-RT-RU-Allowed-LU-LT      (11295),  -- Left U-Turn and Left
                                                         -- Turn Allowed
   prohibit-LT-Allowed-LU-L45-S-R45-RT-RU      (11296),  -- Left Turn Prohibited
                                                         -- (R3-2)
   prohibit-LT-RU-Allowed-LU-L45-S-R45-RT      (11297),
   prohibit-LT-RT-Allowed-LU-L45-S-R45-RU      (11298),  -- Left and Right Turn
                                                         -- Prohibited  (R3-3), Straight
                                                         -- Only
   prohibit-LT-RT-RU-Allowed-LU-L45-S-R45      (11299),
   prohibit-LT-R45-Allowed-LU-L45-S-RT-RU      (11300),
   prohibit-LT-R45-RU-Allowed-LU-L45-S-RT      (11301),
   prohibit-LT-R45-RT-Allowed-LU-L45-S-RU      (11302),
   prohibit-LT-R45-RT-RU-Allowed-LU-L45-S      (11303),
   prohibit-LT-S-Allowed-LU-L45-R45-RT-RU      (11304),  -- Straight Ahead
                                                         -- Prohibited
   prohibit-LT-S-RU-Allowed-LU-L45-R45-RT      (11305),
   prohibit-LT-S-RT-Allowed-LU-L45-R45-RU      (11306),
   prohibit-LT-S-RT-RU-Allowed-LU-L45-R45      (11307),
   prohibit-LT-S-R45-Allowed-LU-L45-RT-RU      (11308),
   prohibit-LT-S-R45-RU-Allowed-LU-L45-RT      (11309),
   prohibit-LT-S-R45-RT-Allowed-LU-L45-RU      (11310),
   prohibit-LT-S-R45-RT-RU-Allowed-LU-L45      (11311),
   prohibit-LT-L45-Allowed-LU-S-R45-RT-RU      (11312),
   prohibit-LT-L45-RU-Allowed-LU-S-R45-RT      (11313),
   prohibit-LT-L45-RT-Allowed-LU-S-R45-RU      (11314),
   prohibit-LT-L45-RT-RU-Allowed-LU-S-R45      (11315),
   prohibit-LT-L45-R45-Allowed-LU-S-RT-RU      (11316),
   prohibit-LT-L45-R45-RU-Allowed-LU-S-RT      (11317),
   prohibit-LT-L45-R45-RT-Allowed-LU-S-RU      (11318),
   prohibit-LT-L45-R45-RT-RU-Allowed-LU-S      (11319),
   prohibit-LT-L45-S-Allowed-LU-R45-RT-RU      (11320),
   prohibit-LT-L45-S-RU-Allowed-LU-R45-RT      (11321),
   prohibit-LT-L45-S-RT-Allowed-LU-R45-RU      (11322),
   prohibit-LT-L45-S-RT-RU-Allowed-LU-R45      (11323),
   prohibit-LT-L45-S-R45-Allowed-LU-RT-RU      (11324),
   prohibit-LT-L45-S-R45-RU-Allowed-LU-RT      (11325),
   prohibit-LT-L45-S-R45-RT-Allowed-LU-RU      (11326),
   prohibit-LT-L45-S-R45-RT-RU-Allowed-LU      (11327),  -- Left U-Turn Allowed
   prohibit-LU-Allowed-LT-L45-S-R45-RT-RU      (11328),  -- Left U-Turn Prohibited
                                                         -- (R3-4)
   prohibit-LU-RU-Allowed-LT-L45-S-R45-RT      (11329),
   prohibit-LU-RT-Allowed-LT-L45-S-R45-RU      (11330),
   prohibit-LU-RT-RU-Allowed-LT-L45-S-R45      (11331),
   prohibit-LU-R45-Allowed-LT-L45-S-RT-RU      (11332),
   prohibit-LU-R45-RU-Allowed-LT-L45-S-RT      (11333),
   prohibit-LU-R45-RT-Allowed-LT-L45-S-RU      (11334),
   prohibit-LU-R45-RT-RU-Allowed-LT-L45-S      (11335),
   prohibit-LU-S-Allowed-LT-L45-R45-RT-RU      (11336),
   prohibit-LU-S-RU-Allowed-LT-L45-R45-RT      (11337),
   prohibit-LU-S-RT-Allowed-LT-L45-R45-RU      (11338),
   prohibit-LU-S-RT-RU-Allowed-LT-L45-R45      (11339),
   prohibit-LU-S-R45-Allowed-LT-L45-RT-RU      (11340),
   prohibit-LU-S-R45-RU-Allowed-LT-L45-RT      (11341),
   prohibit-LU-S-R45-RT-Allowed-LT-L45-RU      (11342),
   prohibit-LU-S-R45-RT-RU-Allowed-LT-L45      (11343),
   prohibit-LU-L45-Allowed-LT-S-R45-RT-RU      (11344),
   prohibit-LU-L45-RU-Allowed-LT-S-R45-RT      (11345),
   prohibit-LU-L45-RT-Allowed-LT-S-R45-RU      (11346),
   prohibit-LU-L45-RT-RU-Allowed-LT-S-R45      (11347),
   prohibit-LU-L45-R45-Allowed-LT-S-RT-RU      (11348),
   prohibit-LU-L45-R45-RU-Allowed-LT-S-RT      (11349),
   prohibit-LU-L45-R45-RT-Allowed-LT-S-RU      (11350),
   prohibit-LU-L45-R45-RT-RU-Allowed-LT-S      (11351),  -- Left Turn and Straight
                                                         -- Ahead Only
   prohibit-LU-L45-S-Allowed-LT-R45-RT-RU      (11352),
   prohibit-LU-L45-S-RU-Allowed-LT-R45-RT      (11353),
   prohibit-LU-L45-S-RT-Allowed-LT-R45-RU      (11354),
   prohibit-LU-L45-S-RT-RU-Allowed-LT-R45      (11355),
   prohibit-LU-L45-S-R45-Allowed-LT-RT-RU      (11356),
   prohibit-LU-L45-S-R45-RU-Allowed-LT-RT      (11357),  -- Left Turn and Right Turn
                                                         -- Only
   prohibit-LU-L45-S-R45-RT-Allowed-LT-RU      (11358),
   prohibit-LU-L45-S-R45-RT-RU-Allowed-LT      (11359),  -- Left Turn Only  (R3-5)
   prohibit-LU-LT-Allowed-L45-S-R45-RT-RU      (11360),  -- Left U-Turn and Left
                                                         -- Turn Prohibited  (R3-18)
   prohibit-LU-LT-RU-Allowed-L45-S-R45-RT      (11361),
   prohibit-LU-LT-RT-Allowed-L45-S-R45-RU      (11362),
   prohibit-LU-LT-RT-RU-Allowed-L45-S-R45      (11363),
   prohibit-LU-LT-R45-Allowed-L45-S-RT-RU      (11364),
   prohibit-LU-LT-R45-RU-Allowed-L45-S-RT      (11365),
   prohibit-LU-LT-R45-RT-Allowed-L45-S-RU      (11366),
   prohibit-LU-LT-R45-RT-RU-Allowed-L45-S      (11367),
   prohibit-LU-LT-S-Allowed-L45-R45-RT-RU      (11368),
   prohibit-LU-LT-S-RU-Allowed-L45-R45-RT      (11369),
   prohibit-LU-LT-S-RT-Allowed-L45-R45-RU      (11370),
   prohibit-LU-LT-S-RT-RU-Allowed-L45-R45      (11371),
   prohibit-LU-LT-S-R45-Allowed-L45-RT-RU      (11372),
   prohibit-LU-LT-S-R45-RU-Allowed-L45-RT      (11373),
   prohibit-LU-LT-S-R45-RT-Allowed-L45-RU      (11374),
   prohibit-LU-LT-S-R45-RT-RU-Allowed-L45      (11375),
   prohibit-LU-LT-L45-Allowed-S-R45-RT-RU      (11376),  -- Right Turn or Straight
                                                         -- Only
   prohibit-LU-LT-L45-RU-Allowed-S-R45-RT      (11377),
   prohibit-LU-LT-L45-RT-Allowed-S-R45-RU      (11378),
   prohibit-LU-LT-L45-RT-RU-Allowed-S-R45      (11379),
   prohibit-LU-LT-L45-R45-Allowed-S-RT-RU      (11380),
   prohibit-LU-LT-L45-R45-RU-Allowed-S-RT      (11381),
   prohibit-LU-LT-L45-R45-RT-Allowed-S-RU      (11382),
   prohibit-LU-LT-L45-R45-RT-RU-Allowed-S      (11383),  -- Straight Ahead Only
                                                         -- (R3-5a)
   prohibit-LU-LT-L45-S-Allowed-R45-RT-RU      (11384),
   prohibit-LU-LT-L45-S-RU-Allowed-R45-RT      (11385),
   prohibit-LU-LT-L45-S-RT-Allowed-R45-RU      (11386),
   prohibit-LU-LT-L45-S-RT-RU-Allowed-R45      (11387),
   prohibit-LU-LT-L45-S-R45-Allowed-RT-RU      (11388),
   prohibit-LU-LT-L45-S-R45-RU-Allowed-RT      (11389),  -- Right Turn Only
   prohibit-LU-LT-L45-S-R45-RT-Allowed-RU      (11390),
   prohibit-LU-LT-L45-S-R45-RT-RU-Allowed-None (11391)   -- All Maneuvers are
                                                         -- Prohibited
   } (0..65535)


VehicleGroupAffected ::= INTEGER  {
   all-vehicles                               (9217),
   bicycles                                   (9218),
   motorcycles                                (9219),  -- to include mopeds as well
   cars                                       (9220),  -- (remapped from ERM value of
                                                       -- zero)
   light-vehicles                             (9221),
   cars-and-light-vehicles                    (9222),
   cars-with-trailers                         (9223),
   cars-with-recreational-trailers            (9224),
   vehicles-with-trailers                     (9225),
   heavy-vehicles                             (9226),
   trucks                                     (9227),  -- Use for RG-190
   buses                                      (9228),
   articulated-buses                          (9229),
   school-buses                               (9230),
   vehicles-with-semi-trailers                (9231),
   vehicles-with-double-trailers              (9232),  -- Alternative Rendering: western
                                                       -- doubles
   high-profile-vehicles                      (9233),
   wide-vehicles                              (9234),
   long-vehicles                              (9235),
   hazardous-loads                            (9236),
   exceptional-loads                          (9237),
   abnormal-loads                             (9238),
   convoys                                    (9239),
   maintenance-vehicles                       (9240),
   delivery-vehicles                          (9241),
   vehicles-with-even-numbered-license-plates (9242),
   vehicles-with-odd-numbered-license-plates  (9243),
   vehicles-with-parking-permits              (9244),
   vehicles-with-catalytic-converters         (9245),
   vehicles-without-catalytic-converters      (9246),
   gas-powered-vehicles                       (9247),
   diesel-powered-vehicles                    (9248),
   lPG-vehicles                               (9249),
   military-convoys                           (9250),
   military-vehicles                          (9251),
   electric-powered-vehicles                  (9252),
   hybrid-powered-vehicles                    (9253),
   inherently-low-emission-vehicles            (9254),
   commercial-vehicles                        (9255),
   runaway-vehicles                           (9256),
   vehicles-with-lugs                         (9257),
   motor-driven-cycles                        (9258),
   recreational-vehicles                      (9259),  -- Use for RVs
   non-motorized-vehicles                     (9260),
   traffic                                    (9261)   -- Refers to all types of
                                                       -- motor traffic, all groups
   } (0..65535)
   -- Classification of vehicles and types of transport


VisibilityAndAirQuality ::= INTEGER  {
   -- Visibility
   dense-fog                (5377),  -- This index is not to be used as a default value
                                     -- for this category
   fog                      (5378),
   patchy-fog               (5379),
   freezing-fog             (5380),
   ice-fog                  (5405),  -- Different than freezing fog, ice fog occurs well
                                     -- below freezing temps and is quite common in the
                                     -- Fairbanks area.
   mist                     (5381),
   haze                     (5382),
   visibility-reduced       (5383),
   visibility-blocked       (5404),  -- Used when signs, trees, etc., block the view
   white-out                (5384),  -- Alternative Rendering: Snow glare
   blowing-snow             (5385),
   smoke-hazard             (5386),
   spray-hazard             (5387),
   low-sun-glare            (5388),  -- Do not use for snow glare
   snow-glare               (5389),
   blowing-dust             (5390),
   blowing-sand             (5391),  -- Hint: dune accumulations
   dust-storms              (5392),
   sandstorms               (5393),
   -- Air Quality
   air-quality-good         (5394),
   air-quality-fair         (5395),
   air-quality-poor         (5396),
   air-quality-very-poor    (5397),
   severe-exhaust-pollution (5398),
   smog-alert               (5399),
   pollen-count-high        (5400),
   pollen-count-medium      (5401),
   pollen-count-low         (5402),
   swarms-of-insects        (5403),
   -- Cancel Types
   fog-clearing             (5499),
   visibility-improved      (5500),
   fog-forecast-withdrawn   (5501),
   pollution-alert-ended    (5502),
   air-quality-improved     (5503)
   } (0..65535)


WarningAdvice ::= INTEGER  {
   risk                                                 (6913),  -- Conditions are more
                                                                 -- likely than "normal"
   watch                                                (6914),  -- Conditions are
                                                                 -- favorable for an
                                                                 -- event to occur
   warning                                              (6915),  -- An event has occurred
                                                                 -- but is not (yet) near
   alert                                                (6916),  -- An event has occurred
                                                                 -- and it is near
   danger                                               (6917),
   danger-of-explosion                                  (6918),
   danger-of-fire                                       (6919),
   extra-police-patrols-in-operation                    (6920),
   look-out-for-vehicles-stopped-under-bridges          (6921),
   increased-risk-of-accident                           (6922),
   rescue-and-recovery-work-in-progress-at-sceneREMOVED (6923),  -- No long used, see
                                                                 -- item 2825
   police-at-scene                                      (6924),
   emergency-vehicles-at-scene                          (6925),
   traffic-being-directed-around-accident-area          (6926),
   police-directing-traffic                             (6927),
   rescue-workers-directing-traffic                     (6928),
   repairs-in-progress                                  (6929),
   pilot-car-in-operation                               (6930),
   look-out-for-flagger                                 (6931),  -- Alternative
                                                                 -- Rendering: look out
                                                                 -- for flagman
   look-out-for-workers                                 (6952),  -- Alternative
                                                                 -- Rendering: workers
   police-checks-in-operation                           (6932),  -- Hint: all types of
                                                                 -- checks
   truck-check-point                                    (6937),
   lockdown                                             (6935),
   security-check-point                                 (6936),
   single-occupancy-vehicle-check-point                 (6938),
   mandatory-speed-limit-in-force                       (6933),
   speed-limit-in-force-for-heavy-vehicles              (6934),
   behind-you                                           (6950),
   ride-with-traffic                                    (6953),
   prepare-to-evacuate-area                             (6954),
   avoid                                                (6955),
   -- MUTCD Signs
   look                                                 (6939),
   photo-enforced                                       (6940),
   traffic-signs                                        (6951),
   traffic-laws                                         (6941),
   use-low-gear                                         (6942),
   bridge-ices-before-road                              (6943),
   speed-checked-by-radar                               (6944),
   speed-checked-by-aircraft                            (6945),
   fines                                                (6946),
   fines-higher                                         (6947),
   fines-doubled                                        (6948),
   fines-tripled                                        (6949),
   -- Cancel Types
   evacuation-canceled                                  (7033),
   warning-canceled                                     (7034),  -- Canceling a warning
                                                                 -- may "revert" to a
                                                                 -- watch
   watch-canceled                                       (7035),
   alert-canceled                                       (7036),  -- Canceling an alert
                                                                 -- may "revert" to a
                                                                 -- warning
   ended                                                (7037),  -- Hint: used for many
                                                                 -- sporting/special
                                                                 -- events
   cleared                                              (7038),
   canceled                                             (7039)
   } (0..65535)


WeatherConditions ::= INTEGER  {
   -- General Weather
   overcast                   (4609),  -- This index is not to be used as a default value
                                       -- for this category
   cloudy                     (4610),
   mostly-cloudy              (4611),
   partly-cloudy              (4612),
   partly-sunny               (4613),
   mostly-sunny               (4614),
   sunny                      (4615),
   fair-skies                 (4616),
   clear-skies                (4617),
   mostly-clear               (4618),
   mostly-dry                 (4619),
   dry                        (4620),
   uV-index-very-high         (4621),
   uV-index-high              (4622),
   uV-index-moderate          (4623),
   uV-index-low               (4624),
   uV-index-very-low          (4625),
   barometric-pressure        (4626),  -- Typically followed by a number and value
   ozone-alert                (4627),
   -- Lighting Types
   lighting-unknown           (4628),
   artificial-exterior-light  (4629),
   artificial-interior-light  (4630),
   darkness                   (4631),  -- Also used when not lighted
   dusk                       (4632),
   dawn                       (4633),
   moonlight                  (4634),
   daylight                   (4635),
   -- Cancel Types
   weather-forecast-withdrawn (4735)
   } (0..65535)


Winds ::= INTEGER  {
   tornado                        (5121),  -- Note that this can be combined with "alert"
                                           -- "warning" etc. This index is not to be
                                           -- used as a default value for this category
   hurricane                      (5122),
   hurricane-force-winds          (5123),
   tropical-storm                 (5124),
   gale-force-winds               (5125),
   storm-force-winds              (5126),
   strong-winds                   (5127),
   moderate-winds                 (5128),
   light-winds                    (5129),
   calm                           (5130),
   gusty-winds                    (5131),
   crosswinds                     (5132),
   windy                          (5133),
   -- Cancel Types
   strong-winds-have-eased        (5246),
   strong-wind-forecast-withdrawn (5247)
   } (0..65535)


WinterDrivingIndex ::= INTEGER  {
   driving-conditions-good                (6401),
   driving-conditions-fair                (6402),
   difficult-driving-conditions           (6403),
   very-difficult-driving-conditions      (6404),
   hazardous-driving-conditions           (6405),
   extremely-hazardous-driving-conditions (6406)
   } (0..65535)
   -- See also the restriction list for phrase items such as chains required


WinterDrivingRestrictions ::= INTEGER  {
   winter-equipment-recommended       (6145),
   winter-equipment-required          (6146),
   snow-chains-recommended            (6147),
   snow-chains-required               (6148),
   snow-chains-prohibited             (6149),
   studded-tires-prohibited           (6150),
   snow-tires-recommended             (6151),
   snow-tires-required                (6152),
   four-wheel-drive-recommended       (6153),
   four-wheel-drive-required          (6154),
   snow-tires-or-chains-recommended   (6155),
   snow-tires-or-chains-required      (6156),
   -- Cancel Types
   winter-driving-requirements-lifted (6271)   -- In early editions this was incorrectly
                                               -- listed as code 6157
   } (0..65535)


ITISEventType ::= CHOICE  {
   trafficConditions                   TrafficConditions,
   accidentsAndIncidents               AccidentsAndIncidents,
   closures                            Closures,
   roadwork                            Roadwork,
   obstruction                         Obstruction,
   delayStatusCancellation             DelayStatusCancellation,
   unusualDriving                      UnusualDriving,
   mobileSituation                     MobileSituation,
   deviceStatus                        DeviceStatus,
   restrictionClass                    RestrictionClass,
   incidentResponseStatus              IncidentResponseStatus,
   disasters                           Disasters,
   disturbances                        Disturbances,
   sportingEvents                      SportingEvents,
   specialEvents                       SpecialEvents,
   parkingInformation                  ParkingInformation,
   systemInformation                   SystemInformation,
   weatherConditions                   WeatherConditions,
   precipitation                       Precipitation,
   winds                               Winds,
   visibilityAndAirQuality             VisibilityAndAirQuality,
   temperature                         Temperature,
   pavementConditions                  PavementConditions,
   winterDrivingRestrictions           WinterDrivingRestrictions,
   winterDrivingIndex                  WinterDrivingIndex,
   suggestionAdvice                    SuggestionAdvice,
   warningAdvice                       WarningAdvice,
   adviceInstructionsRecommendations   AdviceInstructionsRecommendations,
   adviceInstructionsMandatory         AdviceInstructionsMandatory,
   laneRoadway                         LaneRoadway,
   alternateRoute                      AlternateRoute,
   transitMode                         TransitMode,
   vehicleGroupAffected                VehicleGroupAffected,
   travelerGroupAffected               TravelerGroupAffected,
   responderGroupAffected              ResponderGroupAffected,
   incidentResponseEquipment           IncidentResponseEquipment,
   transitOperations                   TransitOperations,
   regulatorySigns                     RegulatoryAndWarningSigns
   }
   -- the set of  ITIS.ITISgroups
   -- a single code representing the top level grouping of ITIS sub-groups
   -- surrounded by the element tag of its sub group


ITIScodeAndText ::= SEQUENCE (SIZE(1..100)) OF SEQUENCE {
  item CHOICE    {
       itis ITIScode,
       text ITIStxt
       } -- # UNTAGGED
  }


END

-- Use of this module defined in SAE J2735
-- Latest document release for this module is Nov 2022
-- Filename: J2735-ITIS-2024-rel-v1.1.asn
--

ITIS
{joint-iso-itu-t (2) country (16) us (840) organization (1) sae (114566)
v2x-communications (1) technical-committees (1) v2x-core (5) technical-reports (1)
j2735 (2735) part-0 (0) asn1-module (1) itis (6) version-1 (1) version-minor-1 (1)}

DEFINITIONS AUTOMATIC TAGS ::=
BEGIN

ITISGenericLocations ::= ENUMERATED  {
   -- Road Related
   on-bridges                  (7937),  -- Not to be used as the default for this
                                        -- category
   in-tunnels                  (7938),
   entering-or-leaving-tunnels (7939),
   on-ramps                    (7940),
   in-road-construction-area   (7941),
   around-a-curve              (7942),
   on-curve                    (8026),
   on-tracks                   (8009),
   in-street                   (8025),  -- As in in-street pad crossing
   shoulder                    (8027),
   on-minor-roads              (7943),
   in-the-opposing-lanes       (7944),
   adjacent-to-roadway         (7945),
   across-tracks               (8024),
   on-bend                     (7946),
   intersection                (8032),
   entire-intersection         (7947),
   in-the-median               (7948),
   moved-to-side-of-road       (7949),
   moved-to-shoulder           (7950),
   on-the-roadway              (7951),  -- Use generic locations/groups affected to
                                        -- make other such phrases
   dip                         (8010),
   traffic-circle              (8011),  -- Used for W2-6 graphic as well. Alt term:
                                        -- roundabout
   crossover                   (8028),
   cross-road                  (8029),  -- Also used for W2-1 Note that in some uses
                                        -- this is one word
   side-road                   (8030),  -- Do not used for W2-2R and W2-2L
   to                          (8014),
   by                          (8015),
   through                     (8016),
   area-of                     (8017),  -- Also area
   under                       (8018),
   over                        (8019),
   from                        (8020),
   approaching                 (8021),
   entering-at                 (8022),  -- Alt form: Entrance
   exiting-at                  (8023),
   -- Terrain & Geography
   in-shaded-areas             (7952),
   in-low-lying-areas          (7953),
   in-the-downtown-area        (7954),
   in-the-inner-city-area      (7955),
   in-parts                    (7956),
   in-some-places              (7957),
   in-the-ditch                (7958),
   in-the-valley               (7959),
   on-hill-top                 (7960),
   near-the-foothills          (7961),
   at-high-altitudes           (7962),
   near-the-lake               (7963),
   near-the-shore              (7964),
   nearby-basin                (8008),
   over-the-crest-of-a-hill    (7965),
   other-than-on-the-roadway   (7966),
   near-the-beach              (7967),
   near-beach-access-point     (7968),
   mountain-pass               (8006),
   lower-level                 (7969),
   upper-level                 (7970),
   -- Transit Travel, Air Travel and Places
   airport                     (7971),
   concourse                   (7972),
   gate                        (7973),
   baggage-claim               (7974),
   customs-point               (7975),
   reservation-center          (8007),
   station                     (7976),
   platform                    (7977),  -- Alternative Rendering:  track
   dock                        (7978),
   depot                       (7979),
   ev-charging-point           (7980),
   information-welcome-point   (7981),  -- Use for Tourist Information as well (D9-10)
   at-rest-area                (7982),
   at-service-area             (7983),
   at-weigh-station            (7984),
   roadside-park               (8033),
   picnic-areas                (7985),
   rest-area                   (7986),
   service-stations            (7987),
   toilets                     (7988),  -- Note also rest rooms in structures
   bus-stop                    (8031),
   park-and-ride-lot           (8012),  -- Not to be used as a mode of travel
   -- Direction of Travel
   on-the-right                (7989),
   on-the-left                 (7990),
   in-the-center               (7991),
   in-the-opposite-direction   (7992),
   cross-traffic               (7993),
   northbound-traffic          (7994),
   eastbound-traffic           (7995),
   southbound-traffic          (7996),
   westbound-traffic           (7997),
   -- Compass Points
   north                       (7998),
   south                       (7999),
   east                        (8000),
   west                        (8001),
   northeast                   (8002),
   northwest                   (8003),
   southeast                   (8004),
   southwest                   (8005),
   ... -- # LOCAL_CONTENT_ITIS
   }


ITISIncidentResponseEquipment ::= ENUMERATED {
   ground-fire-suppression          (9985),
   heavy-ground-equipment           (9986),
   aircraft                         (9988),
   marine-equipment                 (9989),
   support-equipment                (9990),
   medical-rescue-unit              (9991),
   other                            (9993),   -- Depreciated by fire standards, do not
                                              -- use
   ground-fire-suppression-other    (9994),
   engine                           (9995),
   truck-or-aerial                  (9996),
   quint                            (9997),   -- A five-function type of fire
                                              -- apparatus. The units in the
                                              -- movie Backdraft were quints
   tanker-pumper-combination        (9998),
   brush-truck                      (10000),
   aircraft-rescue-firefighting     (10001),
   heavy-ground-equipment-other     (10004),
   dozer-or-plow                    (10005),
   tractor                          (10006),
   tanker-or-tender                 (10008),
   aircraft-other                   (10024),
   aircraft-fixed-wing-tanker       (10025),
   helitanker                       (10026),
   helicopter                       (10027),
   marine-equipment-other           (10034),
   fire-boat-with-pump              (10035),
   boat-no-pump                     (10036),
   support-apparatus-other          (10044),
   breathing-apparatus-support      (10045),
   light-and-air-unit               (10046),
   medical-rescue-unit-other        (10054),
   rescue-unit                      (10055),
   urban-search-rescue-unit         (10056),
   high-angle-rescue                (10057),
   crash-fire-rescue                (10058),
   bLS-unit                         (10059),
   aLS-unit                         (10060),
   mobile-command-post              (10075),  -- Depreciated, do not use
   chief-officer-car                (10076),
   hAZMAT-unit                      (10077),
   type-i-hand-crew                 (10078),
   type-ii-hand-crew                (10079),
   privately-owned-vehicle          (10083),  -- (Often found in volunteer fire teams)
   other-apparatus-resource         (10084),  -- (Remapped from fire code zero)
   ambulance                        (10085),
   bomb-squad-van                   (10086),
   combine-harvester                (10087),
   construction-vehicle             (10088),
   farm-tractor                     (10089),
   grass-cutting-machines           (10090),
   hAZMAT-containment-tow           (10091),
   heavy-tow                        (10092),
   light-tow                        (10094),
   flatbed-tow                      (10114),
   hedge-cutting-machines           (10093),
   mobile-crane                     (10095),
   refuse-collection-vehicle        (10096),
   resurfacing-vehicle              (10097),
   road-sweeper                     (10098),
   roadside-litter-collection-crews (10099),
   salvage-vehicle                  (10100),
   sand-truck                       (10101),
   snowplow                         (10102),
   steam-roller                     (10103),
   swat-team-van                    (10104),
   track-laying-vehicle             (10105),
   unknown-vehicle                  (10106),
   white-lining-vehicle             (10107),  -- Consider using Roadwork "road marking
                                              -- operations" unless objective is to
                                              -- refer to the specific vehicle of this
                                              -- type.  Alternative Rendering: line
                                              -- painting vehicle
   dump-truck                       (10108),
   supervisor-vehicle               (10109),
   snow-blower                      (10110),
   rotary-snow-blower               (10111),
   road-grader                      (10112),  -- Alternative term: motor grader
   steam-truck                      (10113),  -- A special truck that thaws culverts
                                              -- and storm drains
   ... -- # LOCAL_CONTENT_ITIS
   }

ITIStext ::= IA5String (SIZE(1..500))

ITISResponderGroupAffected ::= ENUMERATED {
   emergency-vehicle-units           (9729),  -- Default, to be used when one of
                                              -- the below does not fit better
   federal-law-enforcement-units     (9730),
   state-police-units                (9731),
   county-police-units               (9732),  -- Hint: also sheriff response units
   local-police-units                (9733),
   ambulance-units                   (9734),
   rescue-units                      (9735),
   fire-units                        (9736),
   hAZMAT-units                      (9737),
   light-tow-unit                    (9738),
   heavy-tow-unit                    (9739),
   freeway-service-patrols           (9740),
   transportation-response-units     (9741),
   private-contractor-response-units (9742),
   ... -- # LOCAL_CONTENT_ITIS
   }
   -- These groups are used in coordinated response and staging area information
   -- (rather than typically consumer related)

ITISVehicleGroupAffected ::= ENUMERATED {
   all-vehicles                               (9217),
   bicycles                                   (9218),
   motorcycles                                (9219),  -- to include mopeds as well
   cars                                       (9220),  -- (remapped from ERM value of
                                                       -- zero)
   light-vehicles                             (9221),
   cars-and-light-vehicles                    (9222),
   cars-with-trailers                         (9223),
   cars-with-recreational-trailers            (9224),
   vehicles-with-trailers                     (9225),
   heavy-vehicles                             (9226),
   trucks                                     (9227),
   buses                                      (9228),
   articulated-buses                          (9229),
   school-buses                               (9230),
   vehicles-with-semi-trailers                (9231),
   vehicles-with-double-trailers              (9232),  -- Alternative Rendering:
                                                       -- western doubles
   high-profile-vehicles                      (9233),
   wide-vehicles                              (9234),
   long-vehicles                              (9235),
   hazardous-loads                            (9236),
   exceptional-loads                          (9237),
   abnormal-loads                             (9238),
   convoys                                    (9239),
   maintenance-vehicles                       (9240),
   delivery-vehicles                          (9241),
   vehicles-with-even-numbered-license-plates (9242),
   vehicles-with-odd-numbered-license-plates  (9243),
   vehicles-with-parking-permits              (9244),
   vehicles-with-catalytic-converters         (9245),
   vehicles-without-catalytic-converters      (9246),
   gas-powered-vehicles                       (9247),
   diesel-powered-vehicles                    (9248),
   lPG-vehicles                               (9249),  -- The L is lower case here
   military-convoys                           (9250),
   military-vehicles                          (9251),
   ... -- # LOCAL_CONTENT_ITIS
   }
   -- Classification of vehicles and types of transport

ITIScodesAndText ::= SEQUENCE (SIZE(1..100)) OF SEQUENCE {
  item CHOICE    {
       itis ITIScodes,
       text ITIStext
       } -- # UNTAGGED
  }

ITIScodes ::= INTEGER (0..65535)
END

-- Use of this module defined in SAE J2735
-- Latest document release for this module is Nov 2022
-- Filename: J2735-Common-2024-rel-v1.1.1.asn
--

Common
{joint-iso-itu-t (2) country (16) us (840) organization (1) sae (114566)
v2x-communications (1) technical-committees (1) v2x-core (5) technical-reports (1)
j2735 (2735) part-0 (0) asn1-module (1) common (38) version-1 (1)  version-minor-1 (1)}

DEFINITIONS AUTOMATIC TAGS ::=
BEGIN

IMPORTS
    DSRCmsgID
        FROM MessageFrame {joint-iso-itu-t (2) country (16) us (840) organization (1) sae (114566)
        v2x-communications (1) technical-committees (1) v2x-core (5) technical-reports (1)
        j2735 (2735) part-0 (0) asn1-module (1) messageFrame (1)
        version-1 (1) version-minor-1 (1)}
    Reg-ComputedLane,
    Reg-LaneDataAttribute,
    Reg-NodeAttributeSetXY,
    Reg-NodeOffsetPointXY,
    Reg-Position3D,
    Reg-RequestorType,
    Reg-VehicleClassification,
    Reg-VerticalOffset
        FROM REGION {joint-iso-itu-t (2) country (16) us (840) organization (1) sae (114566)
        v2x-communications (1) technical-committees (1) v2x-core (5) technical-reports (1)
        j2735 (2735) part-0 (0) asn1-module (1) region (2)
        version-1 (1) version-minor-1 (1)}
    ITISVehicleGroupAffected,
    ITISIncidentResponseEquipment,
    ITISResponderGroupAffected
        FROM ITIS {joint-iso-itu-t (2) country (16) us (840) organization (1) sae (114566)
        v2x-communications (1) technical-committees (1) v2x-core (5) technical-reports (1)
        j2735 (2735) part-0 (0) asn1-module (1) itis (6)
        version-1 (1) version-minor-1 (1)}
    VertOffset-B07,
    PivotPointDescription,
    PARTII-EXT-ID-AND-TYPE
        FROM BasicSafetyMessage {joint-iso-itu-t (2) country (16) us (840) organization (1) sae (114566)
        v2x-communications (1) technical-committees (1) v2x-core (5) technical-reports (1)
        j2735 (2735) part-0 (0) asn1-module (1) basicSafetyMessage (7)
        version-1 (1) version-minor-1 (1)} ;



-- Regional extensions support
REG-EXT-ID-AND-TYPE ::= CLASS {
   &id     RegionId UNIQUE,
   &Type
   } WITH SYNTAX {&Type IDENTIFIED BY &id}

RegionalExtension {REG-EXT-ID-AND-TYPE : Set} ::= SEQUENCE {
   regionId     REG-EXT-ID-AND-TYPE.&id( {Set} ),
   regExtValue  REG-EXT-ID-AND-TYPE.&Type( {Set}{@regionId} )
   }






-- -_-_-_-_-_-_-_-_-_-_-_-_-_-_-_-_-_-_-_-_-_-_-_-_-_-_-_-_
--
-- Start of entries from table Data_Frames...
-- This table typically contains data frame entries.
-- -_-_-_-_-_-_-_-_-_-_-_-_-_-_-_-_-_-_-_-_-_-_-_-_-_-_-_-_
--


AccelerationSet4Way ::= SEQUENCE {
   long Acceleration,          -- Along the Vehicle Longitudinal axis
   lat  Acceleration,          -- Along the Vehicle Lateral axis
   vert VerticalAcceleration,  -- Along the Vehicle Vertical axis
   yaw  YawRate
}


AntennaOffsetSet ::= SEQUENCE {
   antOffsetX  Offset-B12, -- a range of +- 20.47 meters
   antOffsetY  Offset-B09, -- a range of +- 2.55 meters
   antOffsetZ  Offset-B10  -- a range of +- 5.11 meters
   }


BrakeSystemStatus ::= SEQUENCE {
   wheelBrakes        BrakeAppliedStatus,
   traction           TractionControlStatus,
   abs                AntiLockBrakeStatus,
   scs                StabilityControlStatus,
   brakeBoost         BrakeBoostApplied,
   auxBrakes          AuxiliaryBrakeStatus
   }


BSMcoreData ::= SEQUENCE {
   msgCnt        MsgCount,
   id            TemporaryID,
   secMark       DSecond,
   lat           Latitude,
   long          Longitude,
   elev          Elevation,
   accuracy      PositionalAccuracy,
   transmission  TransmissionState,
   speed         Speed,
   heading       Heading,
   angle         SteeringWheelAngle,
   accelSet      AccelerationSet4Way,
   brakes        BrakeSystemStatus,
   size          VehicleSize
   }


BumperHeights ::= SEQUENCE {
   front      BumperHeight,
   rear       BumperHeight
   }


ComputedLane ::= SEQUENCE {
   -- Data needed to created a computed lane
   referenceLaneId    LaneID,
                         -- the lane ID upon which this
                         -- computed lane will be based
   -- Lane Offset in X and Y direction
   offsetXaxis        CHOICE {
                         small   DrivenLineOffsetSm,
                         large   DrivenLineOffsetLg
                         },
   offsetYaxis        CHOICE {
                         small   DrivenLineOffsetSm,
                         large   DrivenLineOffsetLg
                         },
                         -- A path X offset value for translations of the
                         -- path's points when creating translated lanes.
                         -- The values found in the reference lane are
                         -- all offset based on the X and Y values from
                         -- the coordinates of the reference lane's
                         -- initial path point.
   -- Lane Rotation
   rotateXY           Angle OPTIONAL,
                         -- A path rotation value for the entire lane
                         -- Observe that this rotates the existing orientation
                         -- of the referenced lane, it does not replace it.
                         -- Rotation occurs about the initial path point.
   -- Lane Path Scale (zooming)
   scaleXaxis         Scale-B12 OPTIONAL,
   scaleYaxis         Scale-B12 OPTIONAL,
                         -- value for translations or zooming of the path's
                         -- points. The values found in the reference lane
                         -- are all expanded or contracted based on the X
                         -- and Y and width values from the coordinates of
                         -- the reference lane's initial path point.
                         -- The Z axis remains untouched.
   regional  SEQUENCE (SIZE(1..4)) OF
             RegionalExtension {{Reg-ComputedLane}} OPTIONAL,
   ...
   }


DDate ::= SEQUENCE {
   year    DYear,
   month   DMonth,
   day     DDay
   }


DDateTime ::= SEQUENCE {
   year    DYear    OPTIONAL,
   month   DMonth   OPTIONAL,
   day     DDay     OPTIONAL,
   hour    DHour    OPTIONAL,
   minute  DMinute  OPTIONAL,
   second  DSecond  OPTIONAL,
   offset  DOffset  OPTIONAL -- time zone
   }


DFullTime ::= SEQUENCE {
   year    DYear,
   month   DMonth,
   day     DDay,
   hour    DHour,
   minute  DMinute
   }


DMonthDay ::= SEQUENCE {
   month   DMonth,
   day     DDay
   }


DTime ::= SEQUENCE {
   hour    DHour,
   minute  DMinute,
   second  DSecond,
   offset  DOffset  OPTIONAL -- time zone
   }


DYearMonth ::= SEQUENCE {
   year    DYear,
   month   DMonth
   }


EmergencyDetails ::= SEQUENCE {
   doNotUse     SSPindex,
   -- always set to 0 and carries no meaning;
   -- legacy field maintained for backward compatibility
   sirenUse     SirenInUse,
   lightsUse    LightbarInUse,
   multi        MultiVehicleResponse,
   events       PrivilegedEvents OPTIONAL,
   responseType ResponseType OPTIONAL,
   ...
   }


FullPositionVector ::= SEQUENCE {
   utcTime             DDateTime OPTIONAL,   -- time with mSec precision
   long                Longitude,            -- 1/10th microdegree
   lat                 Latitude,             -- 1/10th microdegree
   elevation           Elevation  OPTIONAL,  -- units of 0.1 m
   heading             Heading OPTIONAL,
   speed               TransmissionAndSpeed OPTIONAL,
   posAccuracy         PositionalAccuracy OPTIONAL,
   timeConfidence      TimeConfidence OPTIONAL,
   posConfidence       PositionConfidenceSet OPTIONAL,
   speedConfidence     SpeedandHeadingandThrottleConfidence OPTIONAL,
   ...
   }


Header ::= SEQUENCE {
   -- Basic time and sequence values for the message
   year              DYear           OPTIONAL,
   timeStamp         MinuteOfTheYear OPTIONAL,
   secMark           DSecond         OPTIONAL,
   msgIssueRevision  MsgCount        OPTIONAL,
   ...
   }


IntersectionAccessPoint ::= CHOICE {
   lane       LaneID,
   approach   ApproachID,
   connection LaneConnectionID,
   ...
   }


IntersectionReferenceID ::= SEQUENCE {
   region  RoadRegulatorID OPTIONAL,
           -- a globally unique regional assignment value
           -- typical assigned to a regional DOT authority
           -- the value zero shall be used for testing needs
   id      IntersectionID
           -- a unique mapping to the intersection
           -- in question within the above region of use
   }


LaneDataAttribute ::= CHOICE {
    -- Segment attribute types and the data needed for each
    pathEndPointAngle        DeltaAngle,
                             -- adjusts final point/width slant
                             -- of the lane to align with the stop line
    laneCrownPointCenter     RoadwayCrownAngle,
                             -- sets the canter of the road bed
                             -- from centerline point
    laneCrownPointLeft       RoadwayCrownAngle,
                             -- sets the canter of the road bed
                             -- from left edge
    laneCrownPointRight      RoadwayCrownAngle,
                             -- sets the canter of the road bed
                             -- from right edge
    laneAngle                MergeDivergeNodeAngle,
                             -- the angle or direction of another lane
                             -- this is required to support Japan style
                             -- when a merge point angle is required
    speedLimits              SpeedLimitList,
                             -- Reference regulatory speed limits
                             -- used by all segments

    -- Add others as needed, in regional space
    regional  SEQUENCE (SIZE(1..4)) OF
              RegionalExtension {{Reg-LaneDataAttribute}},
    ...
    }


LaneDataAttributeList ::= SEQUENCE (SIZE(1..8)) OF LaneDataAttribute


Node-LLmD-64b ::= SEQUENCE {
   lon  Longitude,
   lat  Latitude
   }


Node-XY-20b ::= SEQUENCE {
   x  Offset-B10,
   y  Offset-B10
   }


Node-XY-22b ::= SEQUENCE {
   x  Offset-B11,
   y  Offset-B11
   }


Node-XY-24b ::= SEQUENCE {
   x  Offset-B12,
   y  Offset-B12
   }


Node-XY-26b ::= SEQUENCE {
   x  Offset-B13,
   y  Offset-B13
   }


Node-XY-28b ::= SEQUENCE {
   x  Offset-B14,
   y  Offset-B14
   }


Node-XY-32b ::= SEQUENCE {
   x  Offset-B16,
   y  Offset-B16
   }


NodeAttributeSetXY ::= SEQUENCE {
   localNode    NodeAttributeXYList OPTIONAL,
                -- Attribute states which pertain to this node point
   disabled     SegmentAttributeXYList OPTIONAL,
                -- Attribute states which are disabled at this node point
   enabled      SegmentAttributeXYList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation
                -- at this node from this node onwards, in 10cm steps
                -- elevations between nodes are a linear taper between pts
                -- the value of zero shall not be sent here
   regional     SEQUENCE (SIZE(1..4)) OF
                RegionalExtension {{Reg-NodeAttributeSetXY}} OPTIONAL,
   ...
   }


NodeAttributeXYList ::= SEQUENCE (SIZE(1..8)) OF NodeAttributeXY


NodeListXY ::= CHOICE {
   nodes     NodeSetXY,
             -- a lane made up of two or more
             -- XY node points and any attributes
             -- defined in those nodes
   computed  ComputedLane,
             -- a lane path computed by translating
             -- the data defined by another lane
   ...
   }


NodeOffsetPointXY ::= CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   regional         RegionalExtension {{Reg-NodeOffsetPointXY}}
                                    -- node which follows is of a
                                    -- regional definition type
   }

NodeSetXY ::= SEQUENCE (SIZE(2..63)) OF NodeXY

NodeXY ::= SEQUENCE {
   delta       NodeOffsetPointXY,
               -- A choice of which X,Y offset value to use
               -- this includes various delta values as well a regional choices
   attributes  NodeAttributeSetXY OPTIONAL,
               -- Any optional Attributes which are needed
               -- This includes changes to the current lane width and elevation
   ...
   }


PathHistory ::= SEQUENCE {
   initialPosition  FullPositionVector    OPTIONAL,
   currGNSSstatus   GNSSstatus            OPTIONAL,
   crumbData        PathHistoryPointList,
   ...
   }


PathHistoryPointList ::= SEQUENCE (SIZE(1..23)) OF PathHistoryPoint


PathHistoryPoint ::= SEQUENCE {
   latOffset       OffsetLL-B18,
   lonOffset       OffsetLL-B18,
   elevationOffset VertOffset-B12,
   timeOffset      TimeOffset,
                   -- Offset backwards in time
   speed           Speed                 OPTIONAL,
                   -- Speed over the reported period
   posAccuracy     PositionalAccuracy    OPTIONAL,
                   -- The accuracy of this value
   heading         CoarseHeading         OPTIONAL,
                   -- overall heading
   ...
   }


PathPrediction ::= SEQUENCE {
   radiusOfCurve RadiusOfCurvature,
                 -- LSB units of 10cm
                 -- straight path to use value of 32767
   confidence    Confidence,
                 -- LSB units of 0.5 percent
   ...
   }


Position3D ::= SEQUENCE {
   lat        Latitude,                -- in 1/10th microdegrees
   long       Longitude,               -- in 1/10th microdegrees
   elevation  Elevation  OPTIONAL,     -- in 10 cm units
   regional   SEQUENCE (SIZE(1..4)) OF
              RegionalExtension {{Reg-Position3D}} OPTIONAL,
   ...
   }


PositionalAccuracy ::= SEQUENCE {
   -- NMEA-183 values expressed in strict ASN form
   semiMajor     SemiMajorAxisAccuracy,
   semiMinor     SemiMinorAxisAccuracy,
   orientation   SemiMajorAxisOrientation
   }


PositionConfidenceSet ::= SEQUENCE {
   pos        PositionConfidence, -- for both horizontal directions
   elevation  ElevationConfidence
   }


PrivilegedEvents ::= SEQUENCE {
   doNotUse   SSPindex,
        -- always set to 0 and carries no meaning;
        -- legacy field maintained for backward compatibility
   -- The active event list
   event   PrivilegedEventFlags,
   ...
   }


RegulatorySpeedLimit ::= SEQUENCE {
   type        SpeedLimitType,
               -- The type of regulatory speed which follows
   speed       Velocity
               -- The speed in units of 0.02 m/s
               -- See Section 11 for converting and translating
               -- speed expressed in mph into units of m/s
   }


RequestorType ::= SEQUENCE {
   -- Defines who is requesting
   role         BasicVehicleRole, -- Basic role of this user at this time
   subrole      RequestSubRole OPTIONAL, -- A local list with role based items

   -- Defines what kind of request (a level of importance in the Priority Scheme)
   request      RequestImportanceLevel OPTIONAL, -- A local list with request items

   -- Additional classification details
   iso3883      Iso3833VehicleType OPTIONAL,
   hpmsType     VehicleType OPTIONAL,  -- HPMS classification types

   regional     RegionalExtension {{Reg-RequestorType}} OPTIONAL,
   ...
   }


RoadSegmentReferenceID ::= SEQUENCE {
   region  RoadRegulatorID OPTIONAL,
           -- a globally unique regional assignment value
           -- typically assigned to a regional DOT authority
           -- the value zero shall be used for testing needs
   id      RoadSegmentID
           -- a unique mapping to the road segment
           -- in question within the above region of use
           -- during its period of assignment and use
           -- note that unlike intersectionID values,
           -- this value can be reused by the region
   }

RTCMheader ::= SEQUENCE {
   status     GNSSstatus,
   offsetSet  AntennaOffsetSet
   }


RTCMmessageList ::= SEQUENCE (SIZE(1..5)) OF RTCMmessage


SegmentAttributeXYList ::= SEQUENCE (SIZE(1..8)) OF SegmentAttributeXY


SpeedandHeadingandThrottleConfidence ::= SEQUENCE {
   heading   HeadingConfidence,
   speed     SpeedConfidence,
   throttle  ThrottleConfidence
   }


SpeedLimitList ::= SEQUENCE (SIZE(1..9)) OF RegulatorySpeedLimit

SchoolBusJ2945Slash1C ::= SEQUENCE {
    flashingAmberLights     BOOLEAN,
    flashingRedLights       BOOLEAN,
   -- School bus safety indicators
    studentsCrossingFront   BOOLEAN OPTIONAL,
    studentsCrossingBehind  BOOLEAN OPTIONAL,
   studentsLoading         BOOLEAN OPTIONAL,
   studentsUnloading      BOOLEAN OPTIONAL,
   wheelchairLiftInUse      BOOLEAN OPTIONAL,
   -- Emergency indicators
    emergencyExitOpen       BOOLEAN OPTIONAL,
    emergencyRequestMedical BOOLEAN OPTIONAL,
    emergencyRequestFire    BOOLEAN OPTIONAL,
    emergencyRequestPolice  BOOLEAN OPTIONAL,
    ...
}

TrailersJ2945Slash1B ::= SEQUENCE (SIZE(1..8), ...) OF TrailerUnitDescJ2945Slash1B

TrailerUnitDescJ2945Slash1B ::= SEQUENCE {
    width       VehicleWidth,
    length      VehicleLength,
    height      VehicleHeight           OPTIONAL,
    weight      TrailerWeight           OPTIONAL,

    -- The front pivot point of the unit
    frontPivot  PivotPointDescription,
    -- The rear pivot point connecting to the next element,
    -- if present and used (implies another unit is connected)
    rearPivot   PivotPointDescription   OPTIONAL,
    bumpers     BumperHeights           OPTIONAL,
    axles       Axles                   OPTIONAL,
    ...
    }

Axles ::= SEQUENCE {
    -- In the following, the value 10 indicates 10 or more axles
    totalAxles  INTEGER (1..10, ...),
    frontAxles  INTEGER (0..10, ...)    OPTIONAL,
    rearAxles   INTEGER (0..10, ...)    OPTIONAL,
    ...
    }

TransmissionAndSpeed ::= SEQUENCE {
   transmisson   TransmissionState,
   speed         Velocity
   }


VehicleClassification ::= SEQUENCE {
   -- Composed of the following elements:

   -- The 'master' V2X list used when space is limited
   keyType         BasicVehicleClass OPTIONAL,

   -- Types used in the MAP/SPAT/SSR/SRM exchanges
   role            BasicVehicleRole OPTIONAL, -- Basic CERT role at a given time
   iso3883         Iso3833VehicleType OPTIONAL,
   hpmsType        VehicleType OPTIONAL,  -- HPMS classification types

   -- ITIS types for classes of vehicle and agency
   vehicleType     ITISVehicleGroupAffected OPTIONAL,
   responseEquip   ITISIncidentResponseEquipment OPTIONAL,
   responderType   ITISResponderGroupAffected OPTIONAL,

   -- Fuel types for vehicles
   fuelType        FuelType OPTIONAL,

   regional        SEQUENCE (SIZE(1..4)) OF
                   RegionalExtension {{Reg-VehicleClassification}} OPTIONAL,
   ...
   }


VehicleID ::= CHOICE {
   entityID     TemporaryID,
   stationID    StationID
   }


VehicleSafetyExtensions ::= SEQUENCE {
   events             VehicleEventFlags     OPTIONAL,
   pathHistory        PathHistory           OPTIONAL,
   pathPrediction     PathPrediction        OPTIONAL,
   lights             ExteriorLights        OPTIONAL,
   ...,
   timestamp          DDateTime             OPTIONAL,  -- Added for security
   height             VehicleHeight         OPTIONAL  -- Added for truck height
   }


VehicleSize ::= SEQUENCE {
   width     VehicleWidth,
   length    VehicleLength
   }


VerticalOffset ::= CHOICE {
   -- Vertical Offset
   -- All below in steps of 10cm above or below the reference ellipsoid
   offset1         VertOffset-B07,  -- with a range of +-   6.3 meters vertical
   offset2         VertOffset-B08,  -- with a range of +-  12.7 meters vertical
   offset3         VertOffset-B09,  -- with a range of +-  25.5 meters vertical
   offset4         VertOffset-B10,  -- with a range of +-  51.1 meters vertical
   offset5         VertOffset-B11,  -- with a range of +- 102.3 meters vertical
   offset6         VertOffset-B12,  -- with a range of +- 204.7 meters vertical
   elevation       Elevation,       -- with a range of -409.5 to + 6143.9 meters
   regional        RegionalExtension {{Reg-VerticalOffset}}
                                    -- offset which follows is of a
                                    -- regional definition type
   }


WiperSet ::= SEQUENCE {
   statusFront    WiperStatus,
   rateFront      WiperRate,
   statusRear     WiperStatus      OPTIONAL,
   rateRear       WiperRate        OPTIONAL
   }




-- -_-_-_-_-_-_-_-_-_-_-_-_-_-_-_-_-_-_-_-_-_-_-_-_-_-_-_-_
--
-- Start of entries from table Data_Elements...
-- This table typically contains data element entries.
-- -_-_-_-_-_-_-_-_-_-_-_-_-_-_-_-_-_-_-_-_-_-_-_-_-_-_-_-_
--



Acceleration ::= INTEGER (-2000..2001)
   -- LSB units are 0.01 m/s^2
   -- the value 2000 shall be used for values greater than 2000
   -- the value -2000 shall be used for values less than -2000
   -- a value of 2001 shall be used for Unavailable

AmbientAirPressure ::= INTEGER (0..255)
   -- 8 Bits in hPa starting at 580 with a resolution of
   -- 2 hPa resulting in a range of 580 to 1088


AmbientAirTemperature ::= INTEGER (0..191) -- in degrees centigrade with a -40 offset
    -- The value 191 shall indicate an unknown value

Angle ::= INTEGER (0..28800)
   -- LSB of 0.0125 degrees
   -- A range of 0 to 359.9875 degrees

AntiLockBrakeStatus ::= ENUMERATED {
   unavailable (0), -- B'00  Vehicle Not Equipped with ABS Brakes
                    --       or ABS Brakes status is unavailable
   off         (1), -- B'01  Vehicle's ABS are Off
   on          (2), -- B'10  Vehicle's ABS are On ( but not Engaged )
   engaged     (3)  -- B'11  Vehicle's ABS control is Engaged on any wheel
   }

ApproachID ::= INTEGER (0..15) -- zero to be used when valid value is unknown

AuxiliaryBrakeStatus ::= ENUMERATED {
   unavailable (0), -- B'00  Vehicle Not Equipped with Aux Brakes
                    --       or Aux Brakes status is unavailable
   off         (1), -- B'01  Vehicle's Aux Brakes are Off
   on          (2), -- B'10  Vehicle's Aux Brakes are On ( Engaged )
   reserved    (3)  -- B'11
   }

BasicVehicleClass ::= INTEGER (0..255)
unknownVehicleClass             BasicVehicleClass ::=  0
                                -- Not Equipped, Not known or unavailable
specialVehicleClass             BasicVehicleClass ::=  1
                                -- Special use
--
--  Basic Passenger Motor Vehicle Types
--
passenger-Vehicle-TypeUnknown   BasicVehicleClass ::=  10 -- default type
passenger-Vehicle-TypeOther     BasicVehicleClass ::=  11
-- various fuel types are handled in another element

--
-- Light Trucks, Pickup, Van, Panel
--
lightTruck-Vehicle-TypeUnknown  BasicVehicleClass ::=  20 -- default type
lightTruck-Vehicle-TypeOther    BasicVehicleClass ::=  21

--
-- Trucks, Various axle types, includes HPMS items
--
truck-Vehicle-TypeUnknown BasicVehicleClass ::=  25 -- default type
truck-Vehicle-TypeOther BasicVehicleClass ::=  26
truck-axleCnt2  BasicVehicleClass ::=  27 -- Two axle, six tire single units
truck-axleCnt3  BasicVehicleClass ::=  28 -- Three axle, single units
truck-axleCnt4  BasicVehicleClass ::=  29 -- Four or more axle, single unit
truck-axleCnt4Trailer BasicVehicleClass ::=  30 -- Four or less axle, single trailer
truck-axleCnt5Trailer BasicVehicleClass ::=  31 -- Five or less axle, single trailer
truck-axleCnt6Trailer BasicVehicleClass ::=  32 -- Six or more axle, single trailer
truck-axleCnt5MultiTrailer BasicVehicleClass ::=  33 -- Five or less axle, multi-trailer
truck-axleCnt6MultiTrailer BasicVehicleClass ::=  34 -- Six axle, multi-trailer
truck-axleCnt7MultiTrailer BasicVehicleClass ::=  35 -- Seven or more axle, multi-trailer

--
-- Motorcycle Types
--
motorcycle-TypeUnknown          BasicVehicleClass ::=  40 -- default type
motorcycle-TypeOther            BasicVehicleClass ::=  41
motorcycle-Cruiser-Standard     BasicVehicleClass ::=  42
motorcycle-SportUnclad          BasicVehicleClass ::=  43
motorcycle-SportTouring         BasicVehicleClass ::=  44
motorcycle-SuperSport           BasicVehicleClass ::=  45
motorcycle-Touring              BasicVehicleClass ::=  46
motorcycle-Trike                BasicVehicleClass ::=  47
motorcycle-wPassengers          BasicVehicleClass ::=  48 -- type not stated

--
-- Transit Types
--
transit-TypeUnknown             BasicVehicleClass ::=  50 -- default type
transit-TypeOther               BasicVehicleClass ::=  51
transit-BRT                     BasicVehicleClass ::=  52
transit-ExpressBus              BasicVehicleClass ::=  53
transit-LocalBus                BasicVehicleClass ::=  54
transit-SchoolBus               BasicVehicleClass ::=  55
transit-FixedGuideway           BasicVehicleClass ::=  56
transit-Paratransit             BasicVehicleClass ::=  57
transit-Paratransit-Ambulance   BasicVehicleClass ::=  58

--
-- Emergency Vehicle Types
--
emergency-TypeUnknown            BasicVehicleClass ::=  60 -- default type
emergency-TypeOther              BasicVehicleClass ::=  61 -- includes federal users
emergency-Fire-Light-Vehicle     BasicVehicleClass ::=  62
emergency-Fire-Heavy-Vehicle     BasicVehicleClass ::=  63
emergency-Fire-Paramedic-Vehicle BasicVehicleClass ::=  64
emergency-Fire-Ambulance-Vehicle BasicVehicleClass ::=  65
emergency-Police-Light-Vehicle   BasicVehicleClass ::=  66
emergency-Police-Heavy-Vehicle   BasicVehicleClass ::=  67
emergency-Other-Responder        BasicVehicleClass ::=  68
emergency-Other-Ambulance        BasicVehicleClass ::=  69

--
-- Other V2X Equipped Travelers
--
otherTraveler-TypeUnknown          BasicVehicleClass ::=  80 -- default type
otherTraveler-TypeOther            BasicVehicleClass ::=  81
otherTraveler-Pedestrian           BasicVehicleClass ::=  82
otherTraveler-Visually-Disabled    BasicVehicleClass ::=  83
otherTraveler-Physically-Disabled  BasicVehicleClass ::=  84
otherTraveler-Bicycle              BasicVehicleClass ::=  85
otherTraveler-Vulnerable-Roadworker BasicVehicleClass ::=  86

--
-- Other V2X Equipped Device Types
--
infrastructure-TypeUnknown      BasicVehicleClass ::=  90 -- default type
infrastructure-Fixed            BasicVehicleClass ::=  91
infrastructure-Movable          BasicVehicleClass ::=  92
equipped-CargoTrailer           BasicVehicleClass ::=  93


BasicVehicleRole ::= ENUMERATED {
    -- Values used in the EU and in the US
    basicVehicle     (0), -- Light duty passenger vehicle type
    publicTransport  (1), -- Used in EU for Transit us
    specialTransport (2), -- Used in EU (e.g., heavy load)
    dangerousGoods   (3), -- Used in EU for any HAZMAT
    roadWork         (4), -- Used in EU for State and Local DOT uses
    roadRescue       (5), -- Used in EU and in the US to include tow trucks.
    emergency        (6), -- Used in EU for Police, Fire and Ambulance units
    safetyCar        (7), -- Used in EU for Escort vehicles
    -- Begin US unique numbering
    none-unknown     (8), -- added to follow current SAE style guidelines
    truck            (9), -- Heavy trucks with additional BSM rights and obligations
    motorcycle      (10), --
    roadSideSource  (11), -- For infrastructure generated calls such as
                          -- fire house, rail infrastructure, roadwork site, etc.
    police          (12), --
    fire            (13), --
    ambulance       (14), -- (does not include private para-transit etc.)
    dot             (15), -- all roadwork vehicles
    transit         (16), -- all transit vehicles
    slowMoving      (17), -- to also include oversize etc.
    stopNgo         (18), -- to include trash trucks, school buses and others
                          -- that routinely disturb the free flow of traffic
    cyclist         (19), --
    pedestrian      (20), -- also includes those with mobility limitations
    nonMotorized    (21), -- other, horse drawn, etc.
    military        (22), --
    ...
    }

BrakeAppliedStatus ::= BIT STRING {
   unavailable (0),  -- When set, the brake applied status is unavailable
   leftFront   (1),  -- Left Front Active
   leftRear    (2),  -- Left Rear Active
   rightFront  (3),  -- Right Front Active
   rightRear   (4)   -- Right Rear Active
   } (SIZE (5))

BrakeBoostApplied ::= ENUMERATED {
   unavailable   (0), -- Vehicle not equipped with brake boost
                      -- or brake boost data is unavailable
   off           (1), -- Vehicle's brake boost is off
   on            (2)  -- Vehicle's brake boost is on (applied)
   }

BumperHeight ::= INTEGER (0..127) -- in units of 0.01 meters from ground surface.

CoarseHeading ::= INTEGER (0..240)
   -- Where the LSB is in units of 1.5 degrees
   -- over a range of 0~358.5 degrees
   -- the value 240 shall be used for unavailable

CodeWord ::= OCTET STRING (SIZE(1..16))
   -- any octet string up to 16 octets

CoefficientOfFriction ::= INTEGER (0..50)
   -- where 0 = 0.00 micro (frictionless), also used when data is unavailable
   -- and  50 = 1.00 micro, in steps of 0.02

Confidence ::= INTEGER (0..200)
   -- LSB units of 0.5 percent

Count ::= INTEGER (0..32)

DDay ::= INTEGER (0..31)  -- units of days

DeltaAngle ::= INTEGER (-150..150)
   -- With an angle range from
   -- negative 150 to positive 150
   -- in one degree steps where zero is directly
   -- along the axis or the lane center line as defined by the
   -- two closest points

DescriptiveName ::= IA5String (SIZE(1..63))

DHour ::= INTEGER (0..31) -- units of hours

DMinute ::= INTEGER (0..60) -- units of minutes

DMonth ::= INTEGER (0..12) -- units of months

DOffset ::= INTEGER (-840..840) -- units of minutes from UTC time

DrivenLineOffsetLg ::= INTEGER (-32767..32767)
   -- LSB units are 1 cm.

DrivenLineOffsetSm ::= INTEGER (-2047..2047)
   -- LSB units are 1 cm.

DSecond ::= INTEGER (0..65535) -- units of milliseconds
   --
   -- DER forms,
   -- All DER forms are now retired and not to be used
   --
   reservedMessageId-D               DSRCmsgID ::=  0 --'00'H
   alaCarteMessage-D                 DSRCmsgID ::=  1 --'01'H ACM
   -- alaCarteMessage-D is Retired, not to be used
   basicSafetyMessage-D              DSRCmsgID ::=  2 --'02'H BSM, heartbeat msg
   basicSafetyMessageVerbose-D       DSRCmsgID ::=  3 --'03'H For testing only
   commonSafetyRequest-D             DSRCmsgID ::=  4 --'04'H CSR
   emergencyVehicleAlert-D           DSRCmsgID ::=  5 --'05'H EVA
   intersectionCollision-D           DSRCmsgID ::=  6 --'06'H ICA
   mapData-D                         DSRCmsgID ::=  7 --'07'H MAP, intersections
   nmeaCorrections-D                 DSRCmsgID ::=  8 --'08'H NMEA
   probeDataManagement-D             DSRCmsgID ::=  9 --'09'H PDM
   probeVehicleData-D                DSRCmsgID ::= 10 --'0A'H PVD
   roadSideAlert-D                   DSRCmsgID ::= 11 --'0B'H RSA
   rtcmCorrections-D                 DSRCmsgID ::= 12 --'0C'H RTCM
   signalPhaseAndTimingMessage-D     DSRCmsgID ::= 13 --'0D'H SPAT
   signalRequestMessage-D            DSRCmsgID ::= 14 --'0E'H SRM
   signalStatusMessage-D             DSRCmsgID ::= 15 --'0F'H SSM
   travelerInformation-D             DSRCmsgID ::= 16 --'10'H TIM
   uperFrame-D                       DSRCmsgID ::= 17 --'11'H UPER frame

Duration ::= INTEGER (0..3600) -- units of seconds

DYear ::= INTEGER (0..4095) -- units of years

ElevationConfidence ::= ENUMERATED {
   unavailable (0),  -- B'0000  Not Equipped or unavailable
   elev-500-00 (1),  -- B'0001  (500 m)
   elev-200-00 (2),  -- B'0010  (200 m)
   elev-100-00 (3),  -- B'0011  (100 m)
   elev-050-00 (4),  -- B'0100  (50 m)
   elev-020-00 (5),  -- B'0101  (20 m)
   elev-010-00 (6),  -- B'0110  (10 m)
   elev-005-00 (7),  -- B'0111  (5 m)
   elev-002-00 (8),  -- B'1000  (2 m)
   elev-001-00 (9),  -- B'1001  (1 m)
   elev-000-50 (10), -- B'1010  (50 cm)
   elev-000-20 (11), -- B'1011  (20 cm)
   elev-000-10 (12), -- B'1100  (10 cm)
   elev-000-05 (13), -- B'1101  (5 cm)
   elev-000-02 (14), -- B'1110  (2 cm)
   elev-000-01 (15)  -- B'1111  (1 cm)
   }  -- Encoded as a 4 bit value

Elevation ::= INTEGER (-4096..61439)
    -- In units of 10 cm steps above or below the reference ellipsoid
    -- Providing a range of -409.5 to + 6143.9 meters
    -- The value -4096 shall be used when Unknown is to be sent

Extent ::= ENUMERATED {
   useInstantlyOnly     (0),
   useFor3meters        (1),
   useFor10meters       (2),
   useFor50meters       (3),
   useFor100meters      (4),
   useFor500meters      (5),
   useFor1000meters     (6),
   useFor5000meters     (7),
   useFor10000meters    (8),
   useFor50000meters    (9),
   useFor100000meters   (10),
   useFor500000meters   (11),
   useFor1000000meters  (12),
   useFor5000000meters  (13),
   useFor10000000meters (14),
   forever              (15)  -- very wide area
   }  -- Encoded as a 4 bit value

ExteriorLights ::= BIT STRING {
   -- All lights off is indicated by no bits set
   lowBeamHeadlightsOn       (0),
   highBeamHeadlightsOn      (1),
   leftTurnSignalOn          (2),
   rightTurnSignalOn         (3),
   hazardSignalOn            (4),
   automaticLightControlOn   (5),
   daytimeRunningLightsOn    (6),
   fogLightOn                (7),
   parkingLightsOn           (8)
   } (SIZE (9, ...))

FrictionInformation ::= SEQUENCE {
    roadSurfaceDescription      DescriptionOfRoadSurface,
    dryOrWet                    RoadSurfaceCondition    OPTIONAL,
    roadRoughness               RoadRoughness           OPTIONAL,
    ...
}

DescriptionOfRoadSurface ::= CHOICE {
    portlandCement PortlandCement,
    asphaltOrTar   AsphaltOrTar,
    gravel         Gravel,
    grass          Grass,
    cinders        Cinders,
    rock           Rock,
    ice            Ice,
    snow           Snow,
    ...
}

PortlandCement ::= SEQUENCE {
    type    PortlandCementType,
    ...
}

PortlandCementType ::= ENUMERATED {
    newSharp,
    traveled,
    trafficPolished,
    ...
}

AsphaltOrTar ::= SEQUENCE {
    type    AsphaltOrTarType,
    ...
}

AsphaltOrTarType ::= ENUMERATED {
    newSharp,
    traveled,
    trafficPolished,
    excessTar,
    ...
}

Gravel ::= SEQUENCE {
    type    GravelType,
    ...
}

GravelType ::= ENUMERATED {
    packedOiled,
    loose,
    ...
}

Grass ::= SEQUENCE {
    type    GrassType,
    ...
}

GrassType ::= ENUMERATED {
    lessThan30Mph,
    ...
}

Cinders ::= SEQUENCE {
    type    CindersType,
    ...
}

CindersType ::= ENUMERATED {
    packed,
    ...
}

Rock ::= SEQUENCE {
    type    RockType,
    ...
}

RockType ::= ENUMERATED {
    crushed,
    ...
}

Ice ::= SEQUENCE {
    type    IceType,
    ...
}

IceType ::= ENUMERATED {
    smooth,
    ...
}

Snow ::= SEQUENCE {
    type    SnowType,
    ...
}

SnowType ::= ENUMERATED {
    packed,
    loose,
    ...
}

RoadSurfaceCondition ::= ENUMERATED { dry, wet, ... }

RoadRoughness ::= SEQUENCE {
    meanVerticalVariation     MeanVariation,
    verticalVariationStdDev   VariationStdDev   OPTIONAL,
    meanHorizontalVariation   MeanVariation     OPTIONAL,
    horizontalVariationStdDev VariationStdDev   OPTIONAL,
    ...
}

MeanVariation ::= INTEGER (0..25000)
    -- Measured in microns (.001 mm)
    -- Range is 0 to 25 mm (0 to 25000 microns)

VariationStdDev ::= INTEGER (0..2500)
    -- Standard deviation in microns

FuelType ::= INTEGER (0..15)
   unknownFuel   FuelType::=  0 -- Gasoline Powered
   gasoline      FuelType::=  1
   ethanol       FuelType::=  2 -- Including blends
   diesel        FuelType::=  3 -- All types
   electric      FuelType::=  4
   hybrid        FuelType::=  5 -- All types
   hydrogen      FuelType::=  6
   natGasLiquid  FuelType::=  7 -- Liquefied
   natGasComp    FuelType::=  8 -- Compressed
   propane       FuelType::=  9


FurtherInfoID ::= OCTET STRING (SIZE(2))
   -- a link to any other incident
   -- information data that may be available
   -- in the normal ATIS incident description
   -- or other messages

GNSSstatus ::= BIT STRING {
   unavailable               (0), -- Not Equipped or unavailable
   isHealthy                 (1),
   isMonitored               (2),
   baseStationType           (3), -- Set to zero if a moving base station,
                                  -- or if a rover device (an OBU),
                                  -- set to one if it is a fixed base station
   aPDOPofUnder5             (4), -- A dilution of precision greater than 5
   inViewOfUnder5            (5), -- Less than 5 satellites in view
   localCorrectionsPresent   (6), -- DGPS type corrections used
   networkCorrectionsPresent (7)  -- RTK type corrections used
   } (SIZE(8))

GrossSpeed ::= INTEGER (0..31) -- Units of 1.00 m/s
   -- The value 30 shall be used for speeds of 30 m/s or greater (67.1 mph)
   -- The value 31 shall indicate that the speed is unavailable

HeadingConfidence ::= ENUMERATED {
   unavailable   (0), -- B'000  Not Equipped or unavailable
   prec10deg     (1), -- B'010  10     degrees
   prec05deg     (2), -- B'011  5      degrees
   prec01deg     (3), -- B'100  1      degrees
   prec0-1deg    (4), -- B'101  0.1    degrees
   prec0-05deg   (5), -- B'110  0.05   degrees
   prec0-01deg   (6), -- B'110  0.01   degrees
   prec0-0125deg (7)  -- B'111  0.0125 degrees, aligned with heading LSB
   }  -- Encoded as a 3 bit value

Heading ::= INTEGER (0..28800)
   -- LSB of 0.0125 degrees
   -- A range of 0 to 359.9875 degrees

HeadingSlice ::= BIT STRING {
   -- Each bit 22.5 degree starting from
   -- North and moving Eastward (clockwise) as one bit
   -- a value of noHeading means no bits set, while a
   -- a value of allHeadings means all bits would be set

   from000-0to022-5degrees  (0),
   from022-5to045-0degrees  (1),
   from045-0to067-5degrees  (2),
   from067-5to090-0degrees  (3),

   from090-0to112-5degrees  (4),
   from112-5to135-0degrees  (5),
   from135-0to157-5degrees  (6),
   from157-5to180-0degrees  (7),

   from180-0to202-5degrees  (8),
   from202-5to225-0degrees  (9),
   from225-0to247-5degrees  (10),
   from247-5to270-0degrees  (11),

   from270-0to292-5degrees  (12),
   from292-5to315-0degrees  (13),
   from315-0to337-5degrees  (14),
   from337-5to360-0degrees  (15)
   }  (SIZE (16))

IntersectionID ::= INTEGER (0..65535)
   -- The values zero through 255 are allocated for testing purposes
   -- Note that the value assigned to an intersection will be
   -- unique within a given regional ID only

Iso3833VehicleType ::= INTEGER (0..100)

TrailerWeight ::= INTEGER (0..64255)

LaneConnectionID ::= INTEGER (0..255)

LaneID ::= INTEGER (0..255)
   -- the value 0 shall be used when the lane ID is
   -- not available or not known
   -- the value 255 is reserved for future use

LaneWidth ::= INTEGER (0..32767) -- units of 1 cm

Latitude ::= INTEGER (-900000000..900000001)
   -- LSB = 1/10 microdegree
   -- Providing a range of plus-minus 90 degrees

LightbarInUse ::= ENUMERATED {
     unavailable         (0),  -- Not Equipped or unavailable
     notInUse            (1),  -- none active
     inUse               (2),
     yellowCautionLights (3),
     schooldBusLights    (4),
     arrowSignsActive    (5),
     slowMovingVehicle   (6),
     freqStops           (7)
     }

Longitude ::= INTEGER (-1799999999..1800000001)
   -- LSB = 1/10 microdegree
   -- Providing a range of plus-minus 180 degrees

Location-quality ::= ENUMERATED {
     loc-qual-bt1m       (0), -- quality better than 1 meter
     loc-qual-bt5m       (1), -- quality better than 5 meters
     loc-qual-bt12m      (2), -- quality better than 12.5 meters
     loc-qual-bt50m      (3), -- quality better than 50 meters
     loc-qual-bt125m     (4), -- quality better than 125 meters
     loc-qual-bt500m     (5), -- quality better than 500 meters
     loc-qual-bt1250m    (6), -- quality better than 1250 meters
     loc-qual-unknown    (7)  -- quality value unknown
     } -- 3 bits, appends with loc-tech to make one octet (0..7)

Location-tech ::= ENUMERATED {
     loc-tech-unknown    (0), -- technology type unknown
     loc-tech-GNSS       (1), -- GNSS technology only
     loc-tech-DGPS       (2), -- differential GNSS (DGPS) technology
     loc-tech-RTK        (3), -- differential GNSS (RTK) technology
     loc-tech-PPP        (4), -- precise point positioning (PPP) technology
     loc-tech-drGPS      (5), -- dead reckoning system w/GPS
     loc-tech-drDGPS     (6), -- dead reckoning system w/DGPS
     loc-tech-dr         (7), -- dead reckoning only
     loc-tech-nav        (8), -- autonomous navigation system on-board
     loc-tech-fault      (9), -- feature is not working
     ...
     }

MergeDivergeNodeAngle ::= INTEGER (-180..180)
   -- In units of 1.5 degrees from north
   -- the value -180 shall be used to represent
   -- data is not available or unknown

MessageBLOB ::= OCTET STRING (SIZE(10..2000))
    -- Final size range may be further
    -- limited by the transport layer used

MinuteOfTheYear ::= INTEGER (0..527040)
   -- the value 527040 shall be used for invalid


MsgCount ::= INTEGER (0..127)

MultiVehicleResponse ::= ENUMERATED {
     unavailable   (0), -- Not Equipped or unavailable
     singleVehicle (1),
     multiVehicle  (2),
     reserved      (3)  -- for future use
     }

NodeAttributeXY ::= ENUMERATED {
   -- Various values which pertain only to the current node point

   -- General Items
   reserved,
   stopLine,             -- point where a mid-path stop line exists
                         -- See also 'do not block' for segments

   -- Path finish details
   roundedCapStyleA,      -- Used to control final path rounded end shape
                          -- with edge of curve at final point in a circle
   roundedCapStyleB,      -- Used to control final path rounded end shape
                          -- with edge of curve extending 50% of width past
                          -- final point in a circle

   -- Topography Points (items with no concept of a distance along the path)
   mergePoint,           -- Japan merge with 1 or more lanes
   divergePoint,         -- Japan diverge with 1 or more lanes
   downstreamStopLine,   -- Japan style downstream intersection
                                   -- (a 2nd intersection) stop line
   downstreamStartNode,  -- Japan style downstream intersection
                                   -- (a 2nd intersection) start node

   -- Pedestrian Support Attributes
   closedToTraffic,      -- where a pedestrian may NOT go
                         -- to be used during construction events
   safeIsland,           -- a pedestrian safe stopping point
                         -- also called a traffic island
                         -- This usage described a point feature on a path,
                         -- other entries can describe a path
   curbPresentAtStepOff, -- the sidewalk to street curb is NOT
                         -- angled where it meets the edge of the
                         -- roadway (user must step up/down)

   -- Lane geometry details  (see standard for defined shapes)
   hydrantPresent,       -- Or other services access
   ...
   }

ObstacleDistance ::= INTEGER (0..32767) -- LSB units of meters

Offset-B09 ::= INTEGER (-256..255)
   -- a range of +- 2.55 meters

Offset-B10 ::= INTEGER (-512..511)
   -- a range of +- 5.11 meters

Offset-B11 ::= INTEGER (-1024..1023)
   -- a range of +- 10.23 meters

Offset-B12 ::= INTEGER (-2048..2047)
   -- a range of +- 20.47 meters

Offset-B13 ::= INTEGER (-4096..4095)
   -- a range of +- 40.95 meters

Offset-B14 ::= INTEGER (-8192..8191)
   -- a range of +- 81.91 meters

Offset-B16 ::= INTEGER (-32768..32767)
   -- a range of +- 327.67 meters

OffsetLL-B18 ::= INTEGER (-131072..131071)
   -- A range of +- 0.0131071 degrees
   -- The value +131071 shall be used for values >= than +0.0131071 degrees
   -- The value -131071 shall be used for values <= than -0.0131071 degrees
   -- The value -131072 shall be used unknown
   -- In LSB units of 0.1 microdegrees (unless a zoom is employed)

PayloadData ::= OCTET STRING (SIZE(1..2048))

PositionConfidence ::= ENUMERATED {
   unavailable (0),  -- B'0000  Not Equipped or unavailable
   a500m   (1), -- B'0001  500m  or about 5 * 10 ^ -3 decimal degrees
   a200m   (2), -- B'0010  200m  or about 2 * 10 ^ -3 decimal degrees
   a100m   (3), -- B'0011  100m  or about 1 * 10 ^ -3 decimal degrees
   a50m    (4), -- B'0100  50m   or about 5 * 10 ^ -4 decimal degrees
   a20m    (5), -- B'0101  20m   or about 2 * 10 ^ -4 decimal degrees
   a10m    (6), -- B'0110  10m   or about 1 * 10 ^ -4 decimal degrees
   a5m     (7), -- B'0111  5m    or about 5 * 10 ^ -5 decimal degrees
   a2m     (8), -- B'1000  2m    or about 2 * 10 ^ -5 decimal degrees
   a1m     (9), -- B'1001  1m    or about 1 * 10 ^ -5 decimal degrees
   a50cm  (10), -- B'1010  0.50m or about 5 * 10 ^ -6 decimal degrees
   a20cm  (11), -- B'1011  0.20m or about 2 * 10 ^ -6 decimal degrees
   a10cm  (12), -- B'1100  0.10m or about 1 * 10 ^ -6 decimal degrees
   a5cm   (13), -- B'1101  0.05m or about 5 * 10 ^ -7 decimal degrees
   a2cm   (14), -- B'1110  0.02m or about 2 * 10 ^ -7 decimal degrees
   a1cm   (15)  -- B'1111  0.01m or about 1 * 10 ^ -7 decimal degrees
   }
   -- Encoded as a 4 bit value

PrioritizationResponseStatus ::= ENUMERATED {
   unknown           (0),
                      -- Unknown state
   requested         (1),
                      -- This prioritization request was detected
                      -- by the traffic controller
   processing        (2),
                      -- Checking request
                      -- (request is in queue, other requests are prior)
   watchOtherTraffic (3),
                      -- Cannot give full permission,
                      -- therefore watch for other traffic
                      -- Note that other requests may be present
   granted           (4),
                      -- Intervention was successful
                      -- and now prioritization is active
   rejected          (5),
                      -- The prioritization or preemption request was
                      -- rejected by the traffic controller
   maxPresence       (6),
                      -- The Request has exceeded maxPresence time
                      -- Used when the controller has determined that
                      -- the requester should then back off and
                      -- request an alternative.
   reserviceLocked   (7),
                      -- Prior conditions have resulted in a reservice
                      -- locked event: the controller requires the
                      -- passage of time before another similar request
                      -- will be accepted
   ...
   }

Priority ::= OCTET STRING (SIZE(1))
    -- Follow definition notes on setting these bits

PrivilegedEventFlags ::= BIT STRING {
   peUnavailable                (0), -- Not Equipped or unavailable
   peEmergencyResponse          (1),
      -- The vehicle is a properly authorized public safety vehicle,
      -- is engaged in a service call, and is currently moving
      -- or is within the roadway.  Note that lights and sirens
      -- may not be evident during any given response call

   -- Emergency and Non Emergency Lights related
   peEmergencyLightsActive      (2),
   peEmergencySoundActive       (3),
   peNonEmergencyLightsActive   (4),
   peNonEmergencySoundActive    (5)

   -- this list is likely to grow with further peer review
   } (SIZE (16))

RadiusOfCurvature ::= INTEGER (-32767..32767)
   -- LSB units of 10cm
   -- A straight path to use value of 32767

RegionId ::= INTEGER (0..255)
   noRegion     RegionId ::= 0  -- Use default supplied stubs
   addGrpA      RegionId ::= 1  -- USA
   addGrpB      RegionId ::= 2  -- Japan
   addGrpC      RegionId ::= 3  -- EU
   addGrpD      RegionId ::= 4  -- Korea
   -- NOTE: new registered regional IDs will be added here
   -- The values 128 and above are for local region use

RequestID ::= INTEGER (0..255)

RequestImportanceLevel ::= ENUMERATED {
    requestImportanceLevelUnKnown  (0),
    requestImportanceLevel1        (1), -- The least important request
    requestImportanceLevel2        (2), -- The values here shall be assigned
    requestImportanceLevel3        (3), -- Meanings based on regional needs
    requestImportanceLevel4        (4), -- for each of the basic roles which
    requestImportanceLevel5        (5), -- are defined elsewhere
    requestImportanceLevel6        (6),
    requestImportanceLevel7        (7),
    requestImportanceLevel8        (8),
    requestImportanceLevel9        (9),
    requestImportanceLevel10      (10),
    requestImportanceLevel11      (11),
    requestImportanceLevel12      (12),
    requestImportanceLevel13      (13),
    requestImportanceLevel14      (14), -- The most important request
    requestImportanceReserved     (15)  -- Reserved for future use
    }

RequestSubRole ::= ENUMERATED {
    requestSubRoleUnKnown    (0),
    requestSubRole1          (1), -- The first type of sub role
    requestSubRole2          (2), -- The values here shall be assigned
    requestSubRole3          (3), -- Meanings based on regional needs
    requestSubRole4          (4), -- to refine and expand the basic
    requestSubRole5          (5), -- roles which are defined elsewhere
    requestSubRole6          (6),
    requestSubRole7          (7),
    requestSubRole8          (8),
    requestSubRole9          (9),
    requestSubRole10        (10),
    requestSubRole11        (11),
    requestSubRole12        (12),
    requestSubRole13        (13),
    requestSubRole14        (14), -- The last type of sub role
    requestSubRoleReserved  (15)  -- Reserved for future use
    }

ResponseType ::= ENUMERATED {
   notInUseOrNotEquipped      (0),
   emergency                  (1),  -- active service call at emergency level
   nonEmergency               (2),  -- also used when returning from service call
   pursuit                    (3),  -- sender driving may be erratic
   stationary                 (4),  -- sender is not moving, stopped along roadside
   slowMoving                 (5),  -- such a mowers, litter trucks, etc.
   stopAndGoMovement          (6),  -- such as school bus or garbage truck
   ...
   }

RestrictionClassID ::= INTEGER (0..255)
   -- An index value to identify data about classes of users
   -- the value used varies with each intersection's
   -- needs and is defined in the map to the assigned
   -- classes of supported users.

RoadAuthorityID ::= CHOICE {
-- This data frame defines the Object Identifier (OID) of the Road Authority.
   fullRdAuthID    FullRoadAuthorityID,
   relRdAuthID     RelativeRoadAuthorityID,
   ...
   }

FullRoadAuthorityID ::= OBJECT IDENTIFIER
-- This data element provides the identifier for the fully specified OID of the
-- Road Authority.

RelativeRoadAuthorityID ::= RELATIVE-OID
-- This data element provides the identifier for the partially specified OID of the
-- Road Authority. This may be used when the base portion of the OID is known.

RoadRegulatorID ::= INTEGER (0..65535)
   -- The value zero shall be used for testing only

RoadSegmentID ::= INTEGER (0..65535)
   -- The values zero to 255 shall be used for testing only
   -- Note that the value assigned to an RoadSegment will be
   -- unique within a given regional ID only during its use

RoadwayCrownAngle ::= INTEGER (-128..127)
    -- In LSB units of 0.3 degrees of angle
    -- over a range of -38.1 to + 38.1 degrees
    -- The value -128 shall be used for unknown
    -- The value zero shall be used for angles
    -- which are between -0.15 and +0.15

RTCMmessage ::= OCTET STRING (SIZE(1..1023))

Scale-B12 ::= INTEGER (-2048..2047)  -- in steps of 0.05 percent

SegmentAttributeXY ::= ENUMERATED {
   -- Various values which can be Enabled and Disabled for a lane segment

   -- General Items
   reserved                  ,
   doNotBlock                ,  -- segment where a vehicle
                                -- may not come to a stop
   whiteLine                 ,  -- segment where lane crossing is not allowed
                                -- such as the final few meters of a lane

   -- Porous Lane states, merging, turn outs, parking etc.

   mergingLaneLeft           ,  -- indicates porous lanes
   mergingLaneRight          ,

   curbOnLeft                ,  -- indicates presence of curbs
   curbOnRight               ,

   loadingzoneOnLeft         ,  -- loading or drop off zones
   loadingzoneOnRight        ,

   turnOutPointOnLeft        ,  -- opening to adjacent street/alley/road
   turnOutPointOnRight       ,

   adjacentParkingOnLeft     , -- side of road parking
   adjacentParkingOnRight    ,

   -- Bike Lane Needs
   adjacentBikeLaneOnLeft    , -- presence of marked bike lanes
   adjacentBikeLaneOnRight   ,
   sharedBikeLane            , -- right of way is shared with bikes
                               -- who may occupy entire lane width
   bikeBoxInFront            ,

   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley
                               -- not used for crossing tracks


   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb
                               -- but at least 1 meter remains open for use
                               -- and at-grade passage

   -- Lane geometry details  (see standard for defined shapes)
   taperToLeft               , -- Used to control final path shape
   taperToRight              , -- Used to control final path shape
   taperToCenterLine         , -- Used to control final path shape

   -- Parking Lane and Curb Attributes
   parallelParking           , --
   headInParking             , -- Parking at an angle with the street
   freeParking               , -- no restriction on use of parking
   timeRestrictionsOnParking , -- Parking is not permitted at all times
                               -- typically used when the 'parking' lane
                               -- becomes a driving lane at times
   costToPark                , -- Used where parking has a cost
   midBlockCurbPresent       , -- a protruding curb near lane edge
   unEvenPavementPresent     , -- a disjoint height at lane edge
   ...
   }

SemiMajorAxisAccuracy ::= INTEGER (0..255)
   -- semi-major axis accuracy at one standard dev
   -- range 0-12.7 meter, LSB = .05m
   -- 254 = any value equal or greater than 12.70 meter
   -- 255 = unavailable semi-major axis value

SemiMajorAxisOrientation ::= INTEGER (0..65535)
   -- orientation of semi-major axis
   -- relative to true north (0~359.9945078786 degrees)
   -- LSB units of 360/65535 deg  = 0.0054932479
   -- a value of 0 shall be 0 degrees
   -- a value of 1 shall be 0.0054932479 degrees
   -- a value of 65534 shall be 359.9945078786 deg
   -- a value of 65535 shall be used for orientation unavailable

SemiMinorAxisAccuracy ::= INTEGER (0..255)
   -- semi-minor axis accuracy at one standard dev
   -- range 0-12.7 meter, LSB = .05m
   -- 254 = any value equal or greater than 12.70 meter
   -- 255 = unavailable semi-minor axis value

SignalGroupID ::= INTEGER (0..255)
    -- The value 0 shall be used when the ID is
    -- not available or not known
    -- the value 255 is reserved to indicate a
    -- permanent green movement state
    -- therefore a simple 8 phase signal controller
    -- device might use 1..9 as its groupIDs

SignalReqScheme ::= OCTET STRING (SIZE(1))
    -- Encoded as follows:
   -- upper nibble:  Preempt #:
    -- Bit 7 (MSB) 1 =  Preempt and 0 =  Priority
    -- Remaining 3 bits:
    -- Range of 0..7. The values of 1..6 represent
    -- the respective controller preempt or Priority
    -- to be activated. The value of 7 represents a
    -- request for a cabinet flash prempt,
    -- while the value of 0 is reserved.

   -- lower nibble:  Strategy #:
    -- Range is 0..15 and is used to specify a desired
    -- strategy (if available).
    -- Currently no strategies are defined and this
    -- should be zero.

SirenInUse ::= ENUMERATED {
     unavailable   (0), -- Not Equipped or unavailable
     notInUse      (1),
     inUse         (2),
     reserved      (3)  -- for future use
     }

SpeedConfidence ::= ENUMERATED {
   unavailable (0), -- Not Equipped or unavailable
   prec100ms   (1), -- 100  meters / sec
   prec10ms    (2), -- 10   meters / sec
   prec5ms     (3), -- 5    meters / sec
   prec1ms     (4), -- 1    meters / sec
   prec0-1ms   (5), -- 0.1  meters / sec
   prec0-05ms  (6), -- 0.05 meters / sec
   prec0-01ms  (7)  -- 0.01 meters / sec
   }

SpeedLimitType ::= ENUMERATED {
    unknown,                    -- Speed limit type not available
    maxSpeedInSchoolZone,       -- Only sent when the limit is active
    maxSpeedInSchoolZoneWhenChildrenArePresent, -- Sent at any time
    maxSpeedInConstructionZone, -- Used for work zones, incident zones, etc.
                                -- where a reduced speed is present
    vehicleMinSpeed,
    vehicleMaxSpeed,            -- Regulatory speed limit for general traffic
    vehicleNightMaxSpeed,

    truckMinSpeed,
    truckMaxSpeed,
    truckNightMaxSpeed,

    vehiclesWithTrailersMinSpeed,
    vehiclesWithTrailersMaxSpeed,
    vehiclesWithTrailersNightMaxSpeed,
    ...
    }

Speed ::= INTEGER (0..8191) -- Units of 0.02 m/s
          -- The value 8191 indicates that
          -- speed is unavailable

SSPindex ::= INTEGER (0..31)

StabilityControlStatus ::= ENUMERATED {
   unavailable (0), -- B'00  Not Equipped with SC
                    --       or SC status is unavailable
   off         (1), -- B'01  Off
   on          (2), -- B'10  On or active (but not engaged)
   engaged     (3)  -- B'11  stability control is Engaged
   }

StationID ::= INTEGER (0..4294967295)

SteeringWheelAngle ::= INTEGER (-126..127)
    -- LSB units of 1.5 degrees, a range of -189 to +189 degrees
    -- +001 = +1.5 deg
    -- -126 = -189 deg and beyond
    -- +126 = +189 deg and beyond
    -- +127 to be used for unavailable

TemporaryID ::= OCTET STRING (SIZE(4))

ThrottleConfidence ::= ENUMERATED {
   unavailable     (0), -- B'00  Not Equipped or unavailable
   prec10percent   (1), -- B'01  10  percent Confidence level
   prec1percent    (2), -- B'10  1   percent Confidence level
   prec0-5percent  (3)  -- B'11  0.5 percent Confidence level
   }

TimeConfidence ::= ENUMERATED {
   unavailable              (0), -- Not Equipped or unavailable
   time-100-000             (1), -- Better than  100 Seconds
   time-050-000             (2), -- Better than  50 Seconds
   time-020-000             (3), -- Better than  20 Seconds
   time-010-000             (4), -- Better than  10 Seconds
   time-002-000             (5), -- Better than  2 Seconds
   time-001-000             (6), -- Better than  1 Second
   time-000-500             (7), -- Better than  0.5 Seconds
   time-000-200             (8), -- Better than  0.2 Seconds
   time-000-100             (9), -- Better than  0.1 Seconds
   time-000-050            (10), -- Better than  0.05 Seconds
   time-000-020            (11), -- Better than  0.02 Seconds
   time-000-010            (12), -- Better than  0.01 Seconds
   time-000-005            (13), -- Better than  0.005 Seconds
   time-000-002            (14), -- Better than  0.002 Seconds
   time-000-001            (15), -- Better than  0.001 Seconds
                                 -- Better than  1 ms
   time-000-000-5          (16), -- Better than  0.000,5 Seconds
   time-000-000-2          (17), -- Better than  0.000,2 Seconds
   time-000-000-1          (18), -- Better than  0.000,1 Seconds
   time-000-000-05         (19), -- Better than  0.000,05 Seconds
   time-000-000-02         (20), -- Better than  0.000,02 Seconds
   time-000-000-01         (21), -- Better than  0.000,01 Seconds
   time-000-000-005        (22), -- Better than  0.000,005 Seconds
   time-000-000-002        (23), -- Better than  0.000,002 Seconds
   time-000-000-001        (24), -- Better than  0.000,001 Seconds
                                 -- Better than  1 microsecond
   time-000-000-000-5      (25), -- Better than  0.000,000,5 Seconds
   time-000-000-000-2      (26), -- Better than  0.000,000,2 Seconds
   time-000-000-000-1      (27), -- Better than  0.000,000,1 Seconds
   time-000-000-000-05     (28), -- Better than  0.000,000,05 Seconds
   time-000-000-000-02     (29), -- Better than  0.000,000,02 Seconds
   time-000-000-000-01     (30), -- Better than  0.000,000,01 Seconds
   time-000-000-000-005    (31), -- Better than  0.000,000,005 Seconds
   time-000-000-000-002    (32), -- Better than  0.000,000,002 Seconds
   time-000-000-000-001    (33), -- Better than  0.000,000,001 Seconds
                                 -- Better than  1 nanosecond
   time-000-000-000-000-5  (34), -- Better than  0.000,000,000,5 Seconds
   time-000-000-000-000-2  (35), -- Better than  0.000,000,000,2 Seconds
   time-000-000-000-000-1  (36), -- Better than  0.000,000,000,1 Seconds
   time-000-000-000-000-05 (37), -- Better than  0.000,000,000,05 Seconds
   time-000-000-000-000-02 (38), -- Better than  0.000,000,000,02 Seconds
   time-000-000-000-000-01 (39)  -- Better than  0.000,000,000,01 Seconds
   }

TimeOffset ::= INTEGER (1..65535)
   -- LSB units of of 10 mSec,
   -- with a range of 0.01 seconds to 10 minutes and 55.34 seconds
   -- a value of 65534 to be used for 655.34 seconds or greater
   -- a value of 65535 to be unavailable

TractionControlStatus ::= ENUMERATED {
   unavailable (0), -- B'00  Not Equipped with traction control
                    --       or traction control status is unavailable
   off         (1), -- B'01  traction control is Off
   on          (2), -- B'10  traction control is On (but not Engaged)
   engaged     (3)  -- B'11  traction control is Engaged
   }

TransitStatus ::= BIT STRING {
    none        (0), -- nothing is active
    anADAuse    (1), -- an ADA access is in progress (wheelchairs, kneeling, etc.)
    aBikeLoad   (2), -- loading of a bicycle is in progress
    doorOpen    (3), -- a vehicle door is open for passenger access
    occM        (4),
    occL        (5)
    -- bits four and five are used to relate the
    -- the relative occupancy of the vehicle, with
    -- 00  as least full and 11 indicating a
    -- close-to or full condition
    } (SIZE(6))

TransmissionState ::= ENUMERATED {
   neutral      (0), -- Neutral
   park         (1), -- Park
   forwardGears (2), -- Forward gears
   reverseGears (3), -- Reverse gears
   reserved1    (4),
   reserved2    (5),
   reserved3    (6),
   unavailable  (7)  -- not-equipped or unavailable value,
   -- Any related speed is relative to the vehicle reference frame used
   }

URL-Link ::= IA5String (SIZE(1..255))

VehicleEventFlags ::= BIT STRING {
   eventHazardLights               (0),
   eventStopLineViolation          (1), -- Intersection Violation
   eventABSactivated               (2),
   eventTractionControlLoss        (3),
   eventStabilityControlactivated  (4),
   eventHazardousMaterials         (5),
   eventReserved1                  (6),
   eventHardBraking                (7),
   eventLightsChanged              (8),
   eventWipersChanged              (9),
   eventFlatTire                   (10),
   eventDisabledVehicle            (11), -- The DisabledVehicle DF may also be sent
   eventAirBagDeployment           (12),
   eventJackKnife                  (13)  -- Applies to vehicles with trailer(s)
   } (SIZE (13, ..., 14))
-- To extend: Append event flags to the list,
-- and update extension marker, e.g., (Size (13, ..., 14..16))

VehicleHeight ::= INTEGER (0..127)
    -- the height of the vehicle
    -- LSB units of 5 cm, range to 6.35 meters

VehicleLength ::= INTEGER (0.. 4095) -- LSB units of 1 cm with a range of >40 meters

VehicleMass ::= INTEGER (0..255)
    -- Values 000 to 080 in steps of 50kg
    -- Values 081 to 200 in steps of 500kg
    -- Values 201 to 253 in steps of 2000kg
    -- The Value 254 shall be used for weights above 170000 kg
    -- The Value 255 shall be used when the value is unknown or unavailable
    -- Encoded such that the values:
    --  81 represents   4500 kg
    -- 181 represents  54500 kg
    -- 253 represents 170000 kg

VehicleType ::= ENUMERATED {
   none                 (0),  -- Not Equipped, Not known or unavailable
   unknown              (1),  -- Does not fit any other category
   special              (2),  -- Special use
   moto                 (3),  -- Motorcycle
   car                  (4),  -- Passenger car
   carOther             (5),  -- Four tire single units
   bus                  (6),  -- Buses
   axleCnt2             (7),  -- Two axle, six tire single units
   axleCnt3             (8),  -- Three axle, single units
   axleCnt4             (9),  -- Four or more axle, single unit
   axleCnt4Trailer      (10), -- Four or less axle, single trailer
   axleCnt5Trailer      (11), -- Five or less axle, single trailer
   axleCnt6Trailer      (12), -- Six or more axle, single trailer
   axleCnt5MultiTrailer (13), -- Five or less axle, multi-trailer
   axleCnt6MultiTrailer (14), -- Six axle, multi-trailer
   axleCnt7MultiTrailer (15),  -- Seven or more axle, multi-trailer
   ...
   }

VehicleWidth ::= INTEGER (0..1023) -- LSB units are 1 cm with a range of >10 meters

Velocity ::= INTEGER (0..8191) -- Units of 0.02 m/s
    -- The value 8191 indicates that
    -- velocity is unavailable

VerticalAccelerationThreshold ::= BIT STRING {
   notEquipped (0), -- Not equipped or off
   leftFront   (1), -- Left Front Event
   leftRear    (2), -- Left Rear Event
   rightFront  (3), -- Right Front Event
   rightRear   (4)  -- Right Rear Event
   } (SIZE(5))

VerticalAcceleration ::= INTEGER (-127..127)
   -- LSB units of 0.02 G steps over -2.52 to +2.54 G
   -- The value +127 shall be used for ranges >= 2.54 G
   -- The value -126 shall be used for ranges <= 2.52 G
   -- The value -127 shall be used for unavailable

VertOffset-B08 ::= INTEGER (-128..127)
   -- LSB units of of 10 cm
   -- with a range of +- 12.7 meters vertical
   -- value  127 to be used for  127 or greater
   -- value -127 to be used for -127 or greater
   -- value -128 to be unavailable

VertOffset-B09 ::= INTEGER (-256..255)
   -- LSB units of of 10 cm
   -- with a range of +- 25.5 meters vertical
   -- value  255 to be used for  255 or greater
   -- value -255 to be used for -255 or greater
   -- value -256 to be unavailable

VertOffset-B10 ::= INTEGER (-512..511)
   -- LSB units of of 10 cm
   -- with a range of +- 51.1 meters vertical
   -- value  511 to be used for  511 or greater
   -- value -511 to be used for -511 or greater
   -- value -512 to be unavailable

VertOffset-B11 ::= INTEGER (-1024..1023)
   -- LSB units of of 10 cm
   -- with a range of +- 102.3 meters vertical
   -- value  1023 to be used for  1023 or greater
   -- value -1023 to be used for -1023 or greater
   -- value -1024 to be unavailable

VertOffset-B12 ::= INTEGER (-2048..2047)
   -- LSB units of of 10 cm
   -- with a range of +- 204.7 meters vertical
   -- value  2047 to be used for  2047 or greater
   -- value -2047 to be used for -2047 or greater
   -- value -2048 to be unavailable

WiperRate ::= INTEGER (0..127) -- units of sweeps per minute

WiperStatus ::= ENUMERATED {
     unavailable         (0), -- Not Equipped with wiper status
                              -- or wiper status is unavailable
     off                 (1),
     intermittent        (2),
     low                 (3),
     high                (4),
     washerInUse         (5), -- washing solution being used
     automaticPresent    (6), -- Auto wiper equipped
     ...
     }

YawRate ::= INTEGER (-32767..32767)
   -- LSB units of 0.01 degrees per second (signed)
END


-- Use of this module defined in SAE J2735
-- Latest document release for this module is Nov 2022
-- Filename: J2735-BasicSafetyMessage-2024-rel-v1.1.2.asn
--

BasicSafetyMessage
{joint-iso-itu-t (2) country (16) us (840) organization (1) sae (114566)
v2x-communications (1) technical-committees (1) v2x-core (5) technical-reports (1)
j2735 (2735) part-0 (0) asn1-module (1) basicSafetyMessage (7)
version-1 (1)  version-minor-1 (1)}

DEFINITIONS AUTOMATIC TAGS ::=
BEGIN

IMPORTS
   Reg-BasicSafetyMessage,
   Reg-EventDescription,
   Reg-SupplementalVehicleExtensions
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   EssPrecipYesNo,
   EssPrecipRate,
   EssPrecipSituation,
   EssSolarRadiation,
   EssMobileFriction
      FROM NTCIP {joint-iso-itu-t (2) country (16) us (840) organization (1) sae (114566)
      v2x-communications (1) technical-committees (1) v2x-core (5) technical-reports (1)
      j2735 (2735) part-0 (0) asn1-module (1) ntcip (5)
      version-1 (1) version-minor-1 (1)}
   ITIScodes,
   ITISGenericLocations
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)}
   BSMcoreData,
   RegionalExtension,
   VehicleSafetyExtensions,
   Priority,
   HeadingSlice,
   Extent,
   ObstacleDistance,
   DDateTime,
   VerticalAccelerationThreshold,
   Offset-B11,
   Angle,
   RTCMheader,
   RTCMmessageList,
   EmergencyDetails,
   BasicVehicleClass,
   VehicleClassification,
   SSPindex,
   TimeOffset,
   Node-XY-24b,
   CoarseHeading,
   VehicleWidth,
   VehicleLength,
   VehicleHeight,
   BumperHeights,
   Offset-B12,
   VehicleMass,
   TrailerWeight,
   AmbientAirTemperature,
   AmbientAirPressure,
   WiperSet,
   CoefficientOfFriction,
   GrossSpeed,
   Axles,
    SchoolBusJ2945Slash1C,
    TrailersJ2945Slash1B
      FROM Common {joint-iso-itu-t (2) country (16) us (840) organization (1) sae (114566)
      v2x-communications (1) technical-committees (1) v2x-core (5) technical-reports (1)
      j2735 (2735) part-0 (0) asn1-module (1) common (38)
      version-1 (1) version-minor-1 (1)}
    RptVehicleClass
        FROM ProbeDataReport {joint-iso-itu-t (2) country (16) us (840) organization (1) sae (114566)
        v2x-communications (1) technical-committees (1) v2x-core (5) technical-reports (1)
        j2945 (2945) slash-c (12) asn1-module (1) probeDataReport (1)
        version-1 (1) version-minor-1 (1)};


BasicSafetyMessage ::= SEQUENCE {
   -- Part I, Sent at all times with each message
   coreData      BSMcoreData,

   -- Part II Content
   partII        SEQUENCE (SIZE(1..8)) OF
                 PartIIcontent {{ BSMpartIIExtension }} OPTIONAL,

   regional      SEQUENCE (SIZE(1..4)) OF
                 RegionalExtension {{Reg-BasicSafetyMessage}} OPTIONAL,
   ...
   }

-- BSM Part II content support
PARTII-EXT-ID-AND-TYPE ::= CLASS {
   &id     PartII-Id UNIQUE,
   &Type
   } WITH SYNTAX {&Type IDENTIFIED BY &id}

PartIIcontent  { PARTII-EXT-ID-AND-TYPE: Set} ::= SEQUENCE {
   partII-Id     PARTII-EXT-ID-AND-TYPE.&id( {Set} ),
   partII-Value  PARTII-EXT-ID-AND-TYPE.&Type( {Set}{@partII-Id} )
   }

PartII-Id ::= INTEGER (0..63)
   vehicleSafetyExt       PartII-Id::= 0  -- VehicleSafetyExtensions
   specialVehicleExt      PartII-Id::= 1  -- SpecialVehicleExtensions
   supplementalVehicleExt PartII-Id::= 2  -- SupplementalVehicleExtensions
   -- NOTE: new registered Part II content IDs will be denoted here

-- In a given message there may be multiple extensions present
-- but at most one instance of each extension type.
BSMpartIIExtension  PARTII-EXT-ID-AND-TYPE ::= {
   { VehicleSafetyExtensions       IDENTIFIED BY vehicleSafetyExt} |
   { SpecialVehicleExtensions      IDENTIFIED BY specialVehicleExt} |
   { SupplementalVehicleExtensions IDENTIFIED BY supplementalVehicleExt} ,
   ...
   }


DisabledVehicle ::= SEQUENCE {
   statusDetails     ITIScodes(523..541),
                     -- Valid range is 532 - 541
                     -- Codes 532 to 541, as taken from J2540:
                     -- Disabled, etc.
                       -- stalled-vehicle (532),
                       -- abandoned-vehicle (533),
                       -- disabled-vehicle (534),
                       -- disabled-truck (535),
                       -- disabled-semi-trailer (536), -^- Alt: disabled
                     -- tractor-trailer
                       -- disabled-bus (537),
                       -- disabled-train (538),
                       -- vehicle-spun-out (539),
                       -- vehicle-on-fire (540),
                       -- vehicle-in-water (541),
   locationDetails   ITISGenericLocations   OPTIONAL,
   ...
   }


EventDescription ::= SEQUENCE {
   typeEvent     ITIScodes,
                 -- A category and an item from that category
                 -- all ITS stds use the same types here
                 -- to explain the type of  the
                 -- alert / danger / hazard involved
   description   SEQUENCE (SIZE(1..8)) OF ITIScodes OPTIONAL,
                 -- Up to eight ITIS code set entries to further
                 -- describe the event, give advice, or any
                 -- other ITIS codes
   priority      Priority OPTIONAL,
                 -- The urgency of this message, a relative
                 -- degree of merit compared with other
                 -- similar messages for this type (not other
                 -- messages being sent by the device), nor
                 -- is it a priority of display urgency
   heading       HeadingSlice  OPTIONAL,
                 -- Applicable headings/direction
   extent        Extent OPTIONAL,
                 -- The spatial distance over which this
                 -- message applies and should be presented to the driver
   regional      SEQUENCE (SIZE(1..4)) OF
                 RegionalExtension {{Reg-EventDescription}} OPTIONAL,
   ...
   }


ObstacleDetection ::= SEQUENCE {
   obDist          ObstacleDistance,        -- Obstacle Distance
   obDirect        ObstacleDirection,       -- Obstacle Direction
   description     ITIScodes(523..541) OPTIONAL,
                                            -- Uses a limited set of ITIS codes
                                            -- Valid range is 532 - 541
   locationDetails ITISGenericLocations OPTIONAL,
   dateTime        DDateTime,               -- Time detected
   vertEvent       VerticalAccelerationThreshold OPTIONAL,
                                            -- Any wheels which have
                                            -- exceeded the acceleration point
   ...
   }


PivotPointDescription ::= SEQUENCE {
   pivotOffset  Offset-B11,
                -- This gives a +- 10m range from the edge of the outline
                -- measured from the edge of the length of this unit
                -- a negative value is offset to inside the units
                -- a positive value is offset beyond the unit
   pivotAngle   Angle,
                -- Measured between the center-line of this unit
                -- and the unit ahead which is pulling it.
                -- This value is required to project the units relative position
   pivots       PivotingAllowed,
                -- true if this unit can rotate about the pivot connection point
   ...
   }

RTCMPackage ::= SEQUENCE {
   -- precise antenna position and noise data for a rover
   rtcmHeader  RTCMheader OPTIONAL,

   -- one or more RTCM messages
   msgs        RTCMmessageList,
   ...
   }


SpecialVehicleExtensions ::= SEQUENCE {
   -- The entire EVA message has been reduced to these items
   vehicleAlerts  EmergencyDetails OPTIONAL,
   -- Description or Direction from an emergency vehicle
   description    EventDescription  OPTIONAL, -- short ITIS description

   -- Trailers for both passenger vehicles and heavy trucks
   doNotUse       TrailerData OPTIONAL,
   --Do not use

   -- HAZMAT and Cargo details to be added in a future revision

   -- Wideload, oversized load to be added in a future revision

   ...
   }


SpeedProfileMeasurementList ::= SEQUENCE (SIZE(1..20)) OF SpeedProfileMeasurement

SpeedProfile ::= SEQUENCE {
   -- Composed of set of measured average speeds
   speedReports SpeedProfileMeasurementList,
   ...
   }


SupplementalVehicleExtensions ::= SEQUENCE {
   -- Note that VehicleEventFlags, ExteriorLights,
   -- PathHistory, and PathPrediction are in VehicleSafetyExtensions

   -- Vehicle Type Classification Data
   classification   BasicVehicleClass        OPTIONAL,
                    -- May be required to be present for non passenger vehicles
   classDetails     VehicleClassification    OPTIONAL,
   vehicleData      VehicleData              OPTIONAL,

   -- Various V2V Probe Data
   doNotUse1          WeatherReport           OPTIONAL,
   --Do not use
   doNotUse2          WeatherProbe            OPTIONAL,
   --Do not use

   -- Detected Obstacle data
   doNotUse3          ObstacleDetection       OPTIONAL,
   --Do not use

   -- Disabled Vehicle Report
   status           DisabledVehicle          OPTIONAL,

   -- Oncoming lane speed reporting
   doNotUse4          SpeedProfile            OPTIONAL,
   --Do not use

   -- Raw GNSS measurements
   doNotUse5          RTCMPackage             OPTIONAL,
   --Do not use

   regional  SEQUENCE (SIZE(1..4)) OF
             RegionalExtension {{Reg-SupplementalVehicleExtensions}} OPTIONAL,
   ...,
   fhwaVehicleClass  RptVehicleClass,
   -- Use FHWA vehicle classes, defined in J2945/C ProbeDataReport

   trailers         TrailersJ2945Slash1B     OPTIONAL,
   -- Used in J2945/1B

   schoolBus         SchoolBusJ2945Slash1C    OPTIONAL
   -- Used in J2945/1C
   }


TrailerData ::= SEQUENCE {
   doNotUse    SSPindex,
   -- always set to 0 and carries no meaning;
   -- legacy field maintained for backward compatibility

   -- Offset connection point details from the
   -- hauling vehicle to the first trailer unit
   connection  PivotPointDescription,

   -- One of more Trailer or Dolly Descriptions
   -- (each called a unit)
   units       TrailerUnitDescriptionList,
   ...
   }

TrailerHistoryPointList ::= SEQUENCE (SIZE(1..23)) OF TrailerHistoryPoint

TrailerHistoryPoint ::= SEQUENCE {
   pivotAngle       Angle,
                    -- angle with respect to the lead unit
   timeOffset       TimeOffset,
                    -- offset backwards in time
   -- Position relative to the hauling Vehicle
   positionOffset   Node-XY-24b,
   elevationOffset  VertOffset-B07 OPTIONAL,
   heading          CoarseHeading OPTIONAL,
                    -- overall heading
   ...
   }


TrailerUnitDescriptionList ::= SEQUENCE (SIZE(1..8)) OF TrailerUnitDescription


TrailerUnitDescription ::= SEQUENCE {
   isDolly          IsDolly, -- if false this is a trailer
   width            VehicleWidth,
   length           VehicleLength,
   height           VehicleHeight OPTIONAL,
   mass             TrailerMass   OPTIONAL,
   bumperHeights    BumperHeights OPTIONAL,
   centerOfGravity  VehicleHeight OPTIONAL,
   -- The front pivot point of the unit
   frontPivot       PivotPointDescription,
   -- The rear pivot point connecting to the next element,
   -- if present and used (implies another unit is connected)
   rearPivot        PivotPointDescription OPTIONAL,

   -- Rear wheel pivot point center-line offset
   -- measured from the rear of the above length
   rearWheelOffset  Offset-B12 OPTIONAL,
                    -- the effective center-line of the wheel set

   -- Current Position relative to the hauling Vehicle
   positionOffset   Node-XY-24b,
   elevationOffset  VertOffset-B07 OPTIONAL,

   -- Past Position history relative to the hauling Vehicle
   crumbData         TrailerHistoryPointList OPTIONAL,
   ...
   }


VehicleData ::= SEQUENCE {
   -- Values for width and length are sent in BSM part I
   height           VehicleHeight         OPTIONAL,
   bumpers          BumperHeights         OPTIONAL,
   mass             VehicleMass           OPTIONAL,
   doNotUse       TrailerWeight         OPTIONAL,
   --Do not use
   ...,
   trailerPresent   BOOLEAN                OPTIONAL,
   pivotPoint      PivotPointDescription   OPTIONAL,
   -- Angle ignored in PivotPointDescription, set to 0
   axles         Axles               OPTIONAL,
   leanAngle      INTEGER (-90..90)      OPTIONAL
   -- In 1 deg increments, for motorcycles only
   }


WeatherProbe ::= SEQUENCE {
   airTemp      AmbientAirTemperature  OPTIONAL,
   airPressure  AmbientAirPressure     OPTIONAL,
   rainRates    WiperSet               OPTIONAL,
   ...
   }


WeatherReport ::= SEQUENCE {
   isRaining        EssPrecipYesNo,
   rainRate         EssPrecipRate       OPTIONAL,
   precipSituation  EssPrecipSituation  OPTIONAL,
   solarRadiation   EssSolarRadiation   OPTIONAL,
   friction         EssMobileFriction   OPTIONAL,
   roadFriction     CoefficientOfFriction     OPTIONAL,
   ...
   }

IsDolly ::= BOOLEAN -- When false indicates a trailer unit

ObstacleDirection ::= Angle

PivotingAllowed ::= BOOLEAN

SpeedProfileMeasurement ::= GrossSpeed

TrailerMass ::= INTEGER (0..255)
   -- object mass with LSB steps of 500 kg (~1100 lbs)
   -- the value zero shall be uaed for an unknown mass value
   -- the value 255 shall be used any mass larger than 127,500kg
   -- a useful range of 0~127.5 metric tons.

VertOffset-B07 ::= INTEGER (-64..63)
   -- LSB units of of 10 cm
   -- with a range of +- 6.3 meters vertical
   -- value  63 to be used for  63 or greater
   -- value -63 to be used for -63 or greater
   -- value -64 to be unavailable
END

-- Use of this module defined in SAE J2735
-- Latest document release for this module is Nov 2022
-- Filename: J2735-CommonSafetyRequest-2024-rel-v1.1.asn
--

CommonSafetyRequest
{joint-iso-itu-t (2) country (16) us (840) organization (1) sae (114566)
v2x-communications (1) technical-committees (1) v2x-core (5) technical-reports (1)
j2735 (2735) part-0 (0) asn1-module (1) commonSafetyRequest (10) version-1 (1)
version-minor-1 (1)}
DEFINITIONS AUTOMATIC TAGS ::=
BEGIN

IMPORTS
   Reg-CommonSafetyRequest
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   MsgCount,
   TemporaryID,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





CommonSafetyRequest ::= SEQUENCE {
   timeStamp   MinuteOfTheYear             OPTIONAL,
   msgCnt      MsgCount                    OPTIONAL,
   id          TemporaryID                 OPTIONAL, -- targeted remote device
   requests    RequestedItemList,
   -- Note: Above no longer uses the same request as probe management
   regional    SEQUENCE (SIZE(1..4)) OF
               RegionalExtension {{Reg-CommonSafetyRequest}} OPTIONAL,
   ...
   }


RequestedItemList ::= SEQUENCE (SIZE(1..32)) OF  RequestedItem

RequestedItem ::= ENUMERATED {
   reserved,
   itemA,
        -- consisting of 2 elements:
        -- lights          ExteriorLights
        -- lightBar        LightbarInUse

   itemB,
        -- consisting of:
        -- wipers  a SEQUENCE

   itemC,
        -- consisting of:
        -- brakeStatus  BrakeSystemStatus

   itemD,
        -- consisting of 2 elements:
        -- brakePressure   BrakeAppliedPressure
        -- roadFriction    CoefficientOfFriction

   itemE,
        -- consisting of 4 elements:
        -- sunData         SunSensor
        -- rainData        RainSensor
        -- airTemp         AmbientAirTemperature
        -- airPres         AmbientAirPressure

   itemF,
        -- consisting of:
        -- steering  a SEQUENCE

   itemG,
        -- consisting of:
        -- accelSets a SEQUENCE

   itemI,
        -- consisting of:
        -- fullPos         FullPositionVector

   itemJ,
        -- consisting of:
        -- position2D      Position2D

   itemK,
        -- consisting of:
        -- position3D      Position3D

   itemL,
        -- consisting of 2 elements:
        -- speedHeadC      SpeedandHeadingConfidence

   itemM,
        -- consisting of:
        -- vehicleData a SEQUENCE

   itemN,
        -- consisting of:
        -- vehicleIdent   VehicleIdent

   itemO,
        -- consisting of:
        -- weatherReport a SEQUENCE

   itemP,
        -- consisting of:
        -- breadcrumbs    PathHistory

   itemQ,
        -- consisting of:
        -- GNSSStatus      GNSSstatus

   ...
   }
END

-- Use of this module defined in SAE J2735
-- Latest document release for this module is Nov 2022
-- Filename: J2735-EmergencyVehicleAlert-2024-rel-v1.1.asn
--

EmergencyVehicleAlert
{joint-iso-itu-t (2) country (16) us (840) organization (1) sae (114566)
v2x-communications (1) technical-committees (1) v2x-core (5) technical-reports (1)
j2735 (2735) part-0 (0) asn1-module (1) emergencyVehicleAlert (11) version-1 (1)
version-minor-1 (1)}
DEFINITIONS AUTOMATIC TAGS ::=
BEGIN

IMPORTS
   Reg-EmergencyVehicleAlert
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   ITISVehicleGroupAffected,
   ITISIncidentResponseEquipment,
   ITISResponderGroupAffected
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)}
   RoadSideAlert
      FROM RoadSideAlert {joint-iso-itu-t (2) country (16) us (840) organization (1) sae (114566)
      v2x-communications (1) technical-committees (1) v2x-core (5) technical-reports (1)
      j2735 (2735) part-0 (0) asn1-module (1) roadSideAlert (16)
      version-1 (1) version-minor-1 (1)}
   MinuteOfTheYear,
   TemporaryID,
   ResponseType,
   EmergencyDetails,
   VehicleMass,
   VehicleType,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





EmergencyVehicleAlert ::= SEQUENCE {
   timeStamp       MinuteOfTheYear OPTIONAL,
   id              TemporaryID OPTIONAL,
   rsaMsg          RoadSideAlert,
         -- the DSRCmsgID inside this
                   -- data frame is set as per the
                   -- RoadSideAlert.
   responseType    ResponseType                   OPTIONAL,
   details         EmergencyDetails               OPTIONAL,
                   -- Combines these 3 items:
                   -- SirenInUse,
                   -- LightbarInUse,
                   -- MultiVehicleReponse,

   mass            VehicleMass                    OPTIONAL,
   basicType       VehicleType                    OPTIONAL,
                                -- gross size and axle cnt

   -- type of vehicle and agency when known
   vehicleType     ITISVehicleGroupAffected      OPTIONAL,
   responseEquip   ITISIncidentResponseEquipment OPTIONAL,
   responderType   ITISResponderGroupAffected    OPTIONAL,
   regional        SEQUENCE (SIZE(1..4)) OF
                   RegionalExtension {{Reg-EmergencyVehicleAlert}} OPTIONAL,
   ...
   }
END

-- Use of this module defined in SAE J2735
-- Latest document release for this module is Nov 2022
-- Filename: J2735-IntersectionCollision-2024-rel-v1.1.asn
--

IntersectionCollision
{joint-iso-itu-t (2) country (16) us (840) organization (1) sae (114566)
v2x-communications (1) technical-committees (1) v2x-core (5) technical-reports (1)
j2735 (2735) part-0 (0) asn1-module (1) intersectionCollision (12) version-1 (1)
version-minor-1 (1)}

DEFINITIONS AUTOMATIC TAGS ::=
BEGIN

IMPORTS
   Reg-IntersectionCollision
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MsgCount,
   TemporaryID,
   MinuteOfTheYear,
   BSMcoreData,
   PathHistory,
   PathPrediction,
   IntersectionReferenceID,
   VehicleEventFlags,
   RegionalExtension,
   ApproachID,
   LaneID
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





IntersectionCollision ::= SEQUENCE {
   msgCnt         MsgCount,
   id             TemporaryID,
   timeStamp      MinuteOfTheYear OPTIONAL,
   partOne        BSMcoreData OPTIONAL,
   path           PathHistory OPTIONAL,
                  -- a set of recent path points forming a history
   pathPrediction PathPrediction OPTIONAL,
                  -- the predicted path
   intersectionID IntersectionReferenceID,
                  -- the applicable Intersection
   laneNumber     ApproachOrLane,
                  -- the best estimate of the applicable Lane or Approach
   eventFlag      VehicleEventFlags,
                  -- used to convey vehicle Panic Events,
                  -- Set to indicate "Intersection Violation"
   regional       SEQUENCE (SIZE(1..4)) OF
                  RegionalExtension {{Reg-IntersectionCollision}} OPTIONAL,
   ...
   }


ApproachOrLane ::= CHOICE {
   approach   ApproachID,
   lane       LaneID
   }
END

-- Use of this module defined in SAE J2735
-- Latest document release for this module is Nov 2022
-- Filename: J2735-MapData-2024-rel-v1.1.asn
--

MapData
{joint-iso-itu-t (2) country (16) us (840) organization (1) sae (114566)
v2x-communications (1) technical-committees (1) v2x-core (5) technical-reports (1)
j2735 (2735) part-0 (0) asn1-module (1) mapData (8) version-1 (1) version-minor-1 (1)}

DEFINITIONS AUTOMATIC TAGS ::=
BEGIN

IMPORTS
   Reg-MapData,
   Reg-GenericLane,
   Reg-IntersectionGeometry,
   Reg-LaneAttributes,
   Reg-SignalControlZone,
   Reg-RestrictionUserType,
   Reg-RoadSegment
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   MsgCount,
   RegionalExtension,
   LaneID,
   IntersectionReferenceID,
   SignalGroupID,
   RestrictionClassID,
   LaneConnectionID,
   DescriptiveName,
   ApproachID,
   NodeListXY,
   Position3D,
   LaneWidth,
   SpeedLimitList,
   RoadSegmentReferenceID,
    RoadAuthorityID
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





MapData ::= SEQUENCE {
   timeStamp         MinuteOfTheYear OPTIONAL,
   msgIssueRevision  MsgCount,
   layerType         LayerType OPTIONAL,
   layerID           LayerID  OPTIONAL,
   intersections     IntersectionGeometryList OPTIONAL,
                     -- All Intersection definitions
   roadSegments      RoadSegmentList OPTIONAL,
                     -- All roadway descriptions

   dataParameters    DataParameters OPTIONAL,
                     -- Any meta data regarding the map contents

   restrictionList   RestrictionClassList OPTIONAL,
                     -- Any restriction ID tables which have
                     -- established for these map entries
   regional          SEQUENCE (SIZE(1..4)) OF
                     RegionalExtension {{Reg-MapData}} OPTIONAL,

   -- NOTE:
   -- Other map data will be added here as it is defined
   -- Examples of the type of content to be added include
   -- curve warnings, construction routes, etc.
   ...
   }


ConnectingLane ::= SEQUENCE {
   lane      LaneID,   -- Index of the connecting lane
   maneuver  AllowedManeuvers OPTIONAL
                       -- The Maneuver between
                       -- the enclosing lane and this lane
                       -- at the stop line to connect them
   }


Connection ::= SEQUENCE {
   -- The subject lane connecting to this lane is:
   connectingLane     ConnectingLane,
                      -- The index of the connecting lane and also
                      -- the maneuver from the current lane to it
   remoteIntersection IntersectionReferenceID OPTIONAL,
                      -- This entry is only used when the
                      -- indicated connecting lane belongs
                      -- to another intersection layout. This
                      -- provides a means to create meshes of lanes

   -- SPAT mapping details at the stop line are:
   signalGroup        SignalGroupID OPTIONAL,
                      -- The matching signal group send by
                      -- the SPAT message for this lane/maneuver.
                      -- Shall be present unless the connectingLane
                      -- has no signal group (is un-signalized)
   userClass          RestrictionClassID OPTIONAL,
                      -- The Restriction Class of users this applies to
                      -- The use of some lane/maneuver and SignalGroupID
                      -- pairings are restricted to selected users.
                      -- When absent, the SignalGroupID applies to all

   -- Movement assist details are given by:
   connectionID       LaneConnectionID OPTIONAL
                      -- An optional connection index used to
                      -- relate this lane connection to any dynamic
                      -- clearance data in the SPAT. Note that
                      -- the index may be shared with other
                      -- connections if the clearance data is common
   }


ConnectsToList ::= SEQUENCE (SIZE(1..16)) OF Connection


DataParameters ::= SEQUENCE {
   processMethod     IA5String(SIZE(1..255)) OPTIONAL,
   processAgency     IA5String(SIZE(1..255)) OPTIONAL,
   lastCheckedDate   IA5String(SIZE(1..255)) OPTIONAL,
   geoidUsed         IA5String(SIZE(1..255)) OPTIONAL,
   ...
   }


GenericLane ::= SEQUENCE {
   laneID           LaneID,
                    -- The unique ID number assigned
                    -- to this lane object
   name             DescriptiveName OPTIONAL,
                    -- often for debug use only
                    -- but at times used to name ped crossings
   ingressApproach  ApproachID OPTIONAL, -- inbound
   egressApproach   ApproachID OPTIONAL, -- outbound
                    -- Approach IDs to which this lane belongs
   laneAttributes   LaneAttributes,
                    -- All Attribute information about
                    -- the basic selected lane type
                    -- Directions of use, Geometric co-sharing
                    -- and Type Specific Attributes
                    -- These Attributes are 'lane - global' that is,
                    -- they are true for the entire length of the lane
   maneuvers        AllowedManeuvers OPTIONAL,
                    -- the permitted maneuvers for this lane
   nodeList         NodeListXY,
                    -- Lane spatial path information as well as
                    -- various Attribute information along the node path
                    -- Attributes found here are more general and may
                    -- come and go over the length of the lane.
   connectsTo       ConnectsToList OPTIONAL,
                    -- a list of other lanes and their signal group IDs
                    -- each connecting lane and its signal group ID
                    -- is given, therefore this element provides the
                    -- information formerly in "signalGroups" in prior
                    -- editions.
   overlays         OverlayLaneList OPTIONAL,
                    -- A list of any lanes which have spatial paths that
                    -- overlay (run on top of, and not simply cross)
                    -- the path of this lane when used. An overlay
                    -- for one lane can be applied to parallel lanes
                    -- without repeating OverlayLaneList for each GenericLane
                    -- entry.
   regional  SEQUENCE (SIZE(1..4)) OF
             RegionalExtension {{Reg-GenericLane}} OPTIONAL,
   ...
   }


IntersectionGeometry ::= SEQUENCE {
   name        DescriptiveName OPTIONAL,
                            -- For debug use only
   id          IntersectionReferenceID,
                            -- A globally unique value set,
                            -- consisting of a regionID and
                            -- intersection ID assignment
   revision    MsgCount,

   -- Required default values about lane descriptions follow
   refPoint    Position3D,  -- The reference from which subsequent
                            -- data points are offset until a new
                            -- point is used.
   laneWidth   LaneWidth OPTIONAL,
                            -- Reference width used by all subsequent
                            -- lanes unless a new width is given
   speedLimits SpeedLimitList OPTIONAL,
                            -- Reference regulatory speed limits
                            -- used by all subsequent
                            -- lanes unless a new speed is given
                            -- See Section 11 for converting and
                            -- translating speed expressed in mph
                            -- into units of m/s
   -- Complete details regarding each lane type in this intersection
   laneSet     LaneList,    -- Data about one or more lanes
                            -- (all lane data is found here)

   -- Data describing how to use and request preemption and
   -- priority services from this intersection (if supported)
   -- NOTE Additonal data may be added in the next release of the
   -- standard at this point to handle this concept
   preemptPriorityData PreemptPriorityList OPTIONAL,
                           -- data about one or more regional
                           -- preempt or priority zones

   regional     SEQUENCE (SIZE(1..4)) OF
                RegionalExtension {{Reg-IntersectionGeometry}} OPTIONAL,
   ...,
   roadAuthorityID         RoadAuthorityID      OPTIONAL
   -- Mandatory if roadRegulatorID is set to 0
   }


IntersectionGeometryList ::= SEQUENCE (SIZE(1..32)) OF IntersectionGeometry


LaneAttributes ::= SEQUENCE {
   directionalUse  LaneDirection,      -- directions of lane use
   sharedWith      LaneSharing,        -- co-users of the lane path
   laneType        LaneTypeAttributes, -- specific lane type data
   regional        RegionalExtension {{Reg-LaneAttributes}} OPTIONAL
   }


LaneList ::= SEQUENCE (SIZE(1..255)) OF GenericLane


LaneTypeAttributes ::= CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   }


OverlayLaneList ::= SEQUENCE (SIZE(1..5)) OF LaneID
   -- The unique ID numbers for any lane object which have
   -- spatial paths that overlay (run on top of, and not
   -- simply cross with) the current lane.
   -- Such as a train path that overlays a motor vehicle
   -- lane object for a roadway segment.


PreemptPriorityList ::= SEQUENCE (SIZE(1..32)) OF SignalControlZone

SignalControlZone ::=  SEQUENCE {
  zone  RegionalExtension {{Reg-SignalControlZone}},
  ...
  }


RestrictionClassAssignment ::= SEQUENCE {
   id       RestrictionClassID,
            -- the unique value (within an intersection or local region)
            -- that is assigned to this group of users
   users    RestrictionUserTypeList
            -- The list of user types/classes
            -- to which this restriction ID applies
   }


RestrictionClassList ::= SEQUENCE (SIZE(1..254)) OF RestrictionClassAssignment


RestrictionUserTypeList ::= SEQUENCE (SIZE(1..16)) OF  RestrictionUserType


RestrictionUserType ::= CHOICE {
   basicType   RestrictionAppliesTo,
               -- a set of the most commonly used types
   regional    SEQUENCE (SIZE(1..4)) OF
               RegionalExtension {{Reg-RestrictionUserType}},
   ...
   }


RoadLaneSetList ::= SEQUENCE (SIZE(1..255)) OF GenericLane


RoadSegmentList ::= SEQUENCE (SIZE(1..32)) OF RoadSegment


RoadSegment ::= SEQUENCE {
   name        DescriptiveName OPTIONAL,
   id          RoadSegmentReferenceID,
                           -- a globally unique value for the segment
   revision    MsgCount,
   -- Required default values about the descriptions to follow
   refPoint    Position3D, -- the reference from which subsequent
                           -- data points are offset until a new
                           -- point is used.
   laneWidth   LaneWidth OPTIONAL,
                            -- Reference width used by all subsequent
                            -- lanes unless a new width is given
   speedLimits SpeedLimitList OPTIONAL,
                            -- Reference regulatory speed limits
                            -- used by all subsequent
                            -- lanes unless a new speed is given
                            -- See Section 11 for converting and
                            -- translating speed expressed in mph
                            -- into units of m/s

   -- Data describing disruptions in the RoadSegment
   -- such as work zones etc will be added here;
   -- in the US the SAE ITIS codes would be used here
   -- The details regarding each lane type in the RoadSegment
   roadLaneSet RoadLaneSetList,

   regional    SEQUENCE (SIZE(1..4)) OF
               RegionalExtension {{Reg-RoadSegment}} OPTIONAL,
   ...
   }

AllowedManeuvers ::= BIT STRING {
    -- With bits as defined:
    -- Allowed maneuvers at path end (stop line)
    -- All maneuvers with bits not set are therefore prohibited !
    -- A value of zero shall be used for unknown, indicating no Maneuver
    maneuverStraightAllowed      (0),
                                  -- a Straight movement is allowed in this lane
    maneuverLeftAllowed          (1),
                                 -- a Left Turn movement is allowed in this lane
    maneuverRightAllowed         (2),
                                 -- a Right Turn movement is allowed in this lane
    maneuverUTurnAllowed         (3),
                                 -- a U turn movement is allowed in this lane
    maneuverLeftTurnOnRedAllowed (4),
                                 -- a Stop, and then proceed when safe movement
                                 -- is allowed in this lane
    maneuverRightTurnOnRedAllowed (5),
                                 -- a Stop, and then proceed when safe movement
                                 -- is allowed in this lane
    maneuverLaneChangeAllowed    (6),
                                 -- a movement which changes to an outer lane
                                 -- on the egress side is allowed in this lane
                                 -- (example: left into either outbound lane)
    maneuverNoStoppingAllowed    (7),
                                 -- the vehicle should not stop at the stop line
                                 -- (example: a flashing green arrow)
    yieldAllwaysRequired         (8),
                                 -- the allowed movements above are not protected
                                 -- (example: an permanent yellow condition)
    goWithHalt                   (9),
                                 -- after making a full stop, may proceed
    caution                      (10),
                                 -- proceed past stop line with caution
    reserved1                    (11)
                                 -- used to align to 12 Bit Field

   } (SIZE(12))

LaneAttributes-Barrier ::= BIT STRING {
   -- With bits as defined:
   median-RevocableLane     (0),
                            -- this lane may be activated or not based
                            -- on the current SPAT message contents
                            -- if not asserted, the lane is ALWAYS present
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))

LaneAttributes-Bike ::= BIT STRING {
   -- With bits as defined:
   bikeRevocableLane       (0),
                           -- this lane may be activated or not based
                           -- on the current SPAT message contents
                           -- if not asserted, the lane is ALWAYS present
   pedestrianUseAllowed    (1),
                           -- The path allows pedestrian traffic,
                           -- if not set, this mode is prohibited
   isBikeFlyOverLane       (2),
                           -- path of lane is not at grade
   fixedCycleTime          (3),
                           -- the phases use preset times
                           -- i.e., there is not a 'push to cross' button
   biDirectionalCycleTimes (4),
                           -- ped walk phases use different SignalGroupID
                           -- for each direction. The first SignalGroupID
                           -- in the first Connection represents 'inbound'
                           -- flow (the direction of travel towards the first
                           -- node point) while second SignalGroupID in the
                           -- next Connection entry represents the 'outbound'
                           -- flow. And use of RestrictionClassID entries
                           -- in the Connect follow this same pattern in pairs.
   isolatedByBarrier       (5),
   unsignalizedSegmentsPresent  (6)
                           -- The lane path consists of one of more segments
                           -- which are not part of a signal group ID

   -- Bits 7~15 reserved and set to zero
   } (SIZE (16))

LaneAttributes-Crosswalk ::= BIT STRING {
   -- With bits as defined:
   -- MUTCD provides no suitable "types" to use here
   crosswalkRevocableLane  (0),
                           -- this lane may be activated or not based
                           -- on the current SPAT message contents
                           -- if not asserted, the lane is ALWAYS present
   bicyleUseAllowed        (1),
                           -- The path allows bicycle traffic,
                           -- if not set, this mode is prohibited
   isXwalkFlyOverLane      (2),
                           -- path of lane is not at grade
   fixedCycleTime          (3),
                           -- ped walk phases use preset times
                           -- i.e., there is not a 'push to cross' button
   biDirectionalCycleTimes (4),
                           -- ped walk phases use different SignalGroupID
                           -- for each direction. The first SignalGroupID
                           -- in the first Connection represents 'inbound'
                           -- flow (the direction of travel towards the first
                           -- node point) while second SignalGroupID in the
                           -- next Connection entry represents the 'outbound'
                           -- flow. And use of RestrictionClassID entries
                           -- in the Connect follow this same pattern in pairs.
   hasPushToWalkButton     (5),
                           -- Has a demand input
   audioSupport            (6),
                           -- audio crossing cues present
   rfSignalRequestPresent  (7),
                           -- Supports RF push to walk technologies
   unsignalizedSegmentsPresent  (8)
                           -- The lane path consists of one of more segments
                           -- which are not part of a signal group ID
   -- Bits 9~15 reserved and set to zero
   } (SIZE (16))

LaneAttributes-Parking ::= BIT STRING {
    -- With bits as defined:
    -- Parking use details, note that detailed restrictions such as
    -- allowed hours are sent by way of ITIS codes in the TIM message
    parkingRevocableLane         (0),
                                 -- this lane may be activated or not based
                                 -- on the current SPAT message contents
                                 -- if not asserted, the lane is ALWAYS present
    parallelParkingInUse         (1),
    headInParkingInUse           (2),
    doNotParkZone                (3),
                                 -- used to denote fire hydrants as well as
                                 -- short disruptions in a parking zone
    parkingForBusUse             (4),
    parkingForTaxiUse            (5),
    noPublicParkingUse           (6)
                                 -- private parking, as in front of
                                 -- private property
   -- Bits 7~15 reserved and set to zero
   } (SIZE (16))

LaneAttributes-Sidewalk ::= BIT STRING {
   -- With bits as defined:
   sidewalk-RevocableLane  (0),
                           -- this lane may be activated or not based
                           -- on the current SPAT message contents
                           -- if not asserted, the lane is ALWAYS present
   bicyleUseAllowed        (1),
                           -- The path allows bicycle traffic,
                           -- if not set, this mode is prohibited
   isSidewalkFlyOverLane   (2),
                           -- path of lane is not at grade
   walkBikes               (3)
                           -- bike traffic must dismount and walk
   -- Bits 4~15 reserved and set to zero
   } (SIZE (16))


LaneAttributes-Striping ::= BIT STRING {
   -- With bits as defined:
    stripeToConnectingLanesRevocableLane      (0),
       -- this lane may be activated or not activated based
       -- on the current SPAT message contents
       -- if not asserted, the lane is ALWAYS present
    stripeDrawOnLeft                          (1),
    stripeDrawOnRight                         (2),
        -- which side of lane to mark
    stripeToConnectingLanesLeft               (3),
    stripeToConnectingLanesRight              (4),
    stripeToConnectingLanesAhead              (5)
        -- the stripe type should be
        -- presented to the user visually
        -- to reflect stripes in the
        -- intersection for the type of
        -- movement indicated
   -- Bits 6~15 reserved and set to zero
   } (SIZE (16))


LaneAttributes-TrackedVehicle ::= BIT STRING {
   -- With bits as defined:
   spec-RevocableLane         (0),
                               -- this lane may be activated or not based
                               -- on the current SPAT message contents
                               -- if not asserted, the lane is ALWAYS present
   spec-commuterRailRoadTrack (1),
   spec-lightRailRoadTrack    (2),
   spec-heavyRailRoadTrack    (3),
   spec-otherRailType         (4)
   -- Bits 5~15 reserved and set to zero
   } (SIZE (16))


LaneAttributes-Vehicle ::= BIT STRING {
   -- With bits as defined:
   isVehicleRevocableLane       (0),
                                 -- this lane may be activated or not based
                                 -- on the current SPAT message contents
                                 -- if not asserted, the lane is ALWAYS present
   isVehicleFlyOverLane         (1),
                                 -- path of lane is not at grade
   hovLaneUseOnly               (2),
   restrictedToBusUse           (3),
   restrictedToTaxiUse          (4),
   restrictedFromPublicUse      (5),
   hasIRbeaconCoverage          (6),
   permissionOnRequest          (7) -- e.g., to inform about a lane for e-cars

   } (SIZE (8,...))

LaneDirection ::= BIT STRING {
   -- With bits as defined:
   -- Allowed directions of travel in the lane object
   -- All lanes are described from the stop line outwards
   ingressPath     (0),
                   -- travel from rear of path to front
                   -- is allowed
   egressPath      (1)
                   -- travel from front of path to rear
                   -- is allowed
   -- Notes:  No Travel, i.e., the lane object type does not support
   --         travel (medians, curbs, etc.) is indicated by not
   --         asserting any bit value
   --         Bi-Directional Travel (such as a ped crosswalk) is
   --         indicated by asserting both of the bits
   } (SIZE (2))

LaneSharing ::= BIT STRING {
    -- With bits as defined:
    overlappingLaneDescriptionProvided  (0),
    -- Assert when another lane object is present to describe the
    -- path of the overlapping shared lane
    -- this construct is not used for lane objects which simply cross
    multipleLanesTreatedAsOneLane       (1),
    -- Assert if the lane object path and width details represents
    -- multiple lanes within it that are not further described

    -- Various modes and type of traffic that may share this lane:
    otherNonMotorizedTrafficTypes       (2), -- horse drawn etc.
    individualMotorizedVehicleTraffic   (3),
    busVehicleTraffic                   (4),
    taxiVehicleTraffic                  (5),
    pedestriansTraffic                  (6),
    cyclistVehicleTraffic               (7),
    trackedVehicleTraffic               (8),
    reserved                            (9)
    } (SIZE (10))
    -- All zeros would indicate 'not shared' and 'not overlapping'

LayerID ::= INTEGER (0..100)

LayerType ::= ENUMERATED {
     none,
     mixedContent, -- two or more of the below types
     generalMapData,
     intersectionData,
     curveData,
     roadwaySectionData,
     parkingAreaData,
     sharedLaneData,
     ...
     }

RestrictionAppliesTo ::= ENUMERATED {
    none,              -- applies to nothing
    equippedTransit,   -- buses etc.
    equippedTaxis,
    equippedOther,     -- other vehicle types with
                       -- necessary signal phase state
                       -- reception equipment
    emissionCompliant, -- regional variants with more
                       -- definitive items also exist
    equippedBicycle,
    weightCompliant,
    heightCompliant,
    -- Items dealing with traveler needs serviced by the infrastructure
    -- These end users (which are not vehicles) are presumed to be suitably equipped
    pedestrians,
    slowMovingPersons,
    wheelchairUsers,
    visualDisabilities,
    audioDisabilities,  -- hearing
    otherUnknownDisabilities,
    ...
    }
END

-- Use of this module defined in SAE J2735
-- Latest document release for this module is Nov 2022
-- Filename: J2735-NMEAcorrections-2024-rel-v1.1.asn
--

NMEAcorrections
{joint-iso-itu-t (2) country (16) us (840) organization (1) sae (114566)
v2x-communications (1) technical-committees (1) v2x-core (5) technical-reports (1)
j2735 (2735) part-0 (0) asn1-module (1) nmeaCorrections (13) version-1 (1) version-minor-1 (1)}

DEFINITIONS AUTOMATIC TAGS ::=
BEGIN

IMPORTS
   Reg-NMEAcorrections
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





NMEAcorrections ::= SEQUENCE {
   timeStamp MinuteOfTheYear    OPTIONAL,
   rev       NMEA-Revision      OPTIONAL,
             -- the specific edition of the standard
             -- that is being sent, 4.x at the time of publication
   msg       NMEA-MsgType       OPTIONAL,
             -- the message and sub-message type, as
             -- defined in the revision being used
   -- NOTE The message type is also in the payload expressed as a string,
   wdCount   ObjectCount        OPTIONAL,
             -- a count of octets to follow
             -- observe that not all NMEA sentences are limited to 82 characters
   payload   NMEA-Payload,
   regional  SEQUENCE (SIZE(1..4)) OF
             RegionalExtension {{Reg-NMEAcorrections}} OPTIONAL,
   ...
   }

NMEA-MsgType ::= INTEGER (0..32767)

NMEA-Payload ::= OCTET STRING (SIZE(1..1023))

NMEA-Revision ::= ENUMERATED {
     unknown       (0), -- default value
     reserved      (1),
     rev1          (2),
     rev2          (3), -- used for 2.x
     rev3          (4), -- used for 3.x
     rev4          (5), -- used for 4.x  (NMEA 4.00 Published November 2008)
     rev5          (6),
     ...
     }

ObjectCount ::= INTEGER (0..1023) -- a count of objects
END

-- Use of this module defined in SAE J2735
-- Latest document release for this module is Nov 2022
-- Filename: J2735-NTCIP-2024-rel-v1.1.asn
--

NTCIP
{joint-iso-itu-t (2) country (16) us (840) organization (1) sae (114566)
v2x-communications (1) technical-committees (1) v2x-core (5) technical-reports (1)
j2735 (2735) part-0 (0) asn1-module (1) ntcip (5) version-1 (1) version-minor-1 (1)}

DEFINITIONS AUTOMATIC TAGS ::=
BEGIN



EssMobileFriction ::= INTEGER (0..101)

EssPrecipRate ::= INTEGER (0..65535)

EssPrecipSituation ::= ENUMERATED {
   other (1),
   unknown (2),
   noPrecipitation (3),
   unidentifiedSlight (4),
   unidentifiedModerate (5),
   unidentifiedHeavy (6),
   snowSlight (7),
   snowModerate (8),
   snowHeavy (9),
   rainSlight (10),
   rainModerate (11),
   rainHeavy (12),
   frozenPrecipitationSlight (13),
   frozenPrecipitationModerate (14),
   frozenPrecipitationHeavy (15)
   }

EssPrecipYesNo ::= ENUMERATED {precip (1), noPrecip (2), error (3)}

EssSolarRadiation ::= INTEGER (0..65535)
END

-- Use of this module defined in SAE J2735
-- Latest document release for this module is Nov 2022
-- Filename: J2735-PersonalSafetyMessage-2024-rel-v1.1.asn
--

PersonalSafetyMessage
{joint-iso-itu-t (2) country (16) us (840) organization (1) sae (114566)
v2x-communications (1) technical-committees (1) v2x-core (5) technical-reports (1)
j2735 (2735) part-0 (0) asn1-module (1) personalSafetyMessage (21)
version-1 (1) version-minor-1 (1)}

DEFINITIONS AUTOMATIC TAGS ::=
BEGIN

IMPORTS
   Reg-PersonalSafetyMessage
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   DSecond,
   MsgCount,
   TemporaryID,
   Position3D,
   PositionalAccuracy,
   Velocity,
   Heading,
   AccelerationSet4Way,
   PathHistory,
   PathPrediction,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





PersonalSafetyMessage ::= SEQUENCE {
   basicType           PersonalDeviceUserType,
   secMark             DSecond,
   msgCnt              MsgCount,
   id                  TemporaryID,
   position            Position3D, --  Lat, Long, Elevation
   accuracy            PositionalAccuracy,
   speed               Velocity,
   heading             Heading,
   accelSet            AccelerationSet4Way        OPTIONAL,
   pathHistory         PathHistory                OPTIONAL,
   pathPrediction      PathPrediction             OPTIONAL,
   propulsion          PropelledInformation       OPTIONAL,
   useState            PersonalDeviceUsageState   OPTIONAL,
   crossRequest        PersonalCrossingRequest    OPTIONAL,
   crossState          PersonalCrossingInProgress OPTIONAL,
   clusterSize         NumberOfParticipantsInCluster        OPTIONAL,
   clusterRadius       PersonalClusterRadius      OPTIONAL,
   eventResponderType  PublicSafetyEventResponderWorkerType OPTIONAL,
   activityType        PublicSafetyAndRoadWorkerActivity    OPTIONAL,
   activitySubType     PublicSafetyDirectingTrafficSubType  OPTIONAL,
   assistType          PersonalAssistive          OPTIONAL,
   sizing              UserSizeAndBehaviour       OPTIONAL,
   attachment          Attachment                 OPTIONAL,
   attachmentRadius    AttachmentRadius           OPTIONAL,
   animalType          AnimalType                 OPTIONAL,

   regional SEQUENCE (SIZE(1..4)) OF
            RegionalExtension {{Reg-PersonalSafetyMessage}} OPTIONAL,
   ...
   }


PropelledInformation ::= CHOICE {
   human   HumanPropelledType, -- PersonalDeviceUserType would be a aPEDESTRIAN
   animal  AnimalPropelledType,
   motor   MotorizedPropelledType,
   ...
}

AnimalPropelledType ::= ENUMERATED {
   unavailable         (0),
   otherTypes          (1), -- any method not listed below
   animalMounted       (2), -- as in horseback
   animalDrawnCarriage (3),
   ...
}

AnimalType ::= ENUMERATED {
   unavailable    (0),
   serviceUse     (1),  -- Includes guide or police animals
   pet            (2),
   farm           (3),
   ...
   }

Attachment ::= ENUMERATED {
   unavailable                  (0), -- has some unknown attachment type
   stroller                     (1),
   bicycleTrailer               (2),
   cart                         (3),
   wheelchair                   (4),
   otherWalkAssistAttachments   (5),
   pet                          (6),
   ...
   }

AttachmentRadius ::= INTEGER (0..200) -- In LSB units of one decimeter

MotorizedPropelledType ::= ENUMERATED {
   unavailable         (0),
   otherTypes          (1), -- any method not listed below
   wheelChair          (2),
   bicycle             (3),
   scooter             (4),
   selfBalancingDevice (5), -- such as Segway
   ...
}

NumberOfParticipantsInCluster ::= ENUMERATED {
   unavailable  (0),
   small        (1),   -- 2-5
   medium       (2),   -- 6-10
   large        (3),   -- >10
   ...
   }

HumanPropelledType ::= ENUMERATED {
   unavailable        (0),
   otherTypes         (1), -- any method not listed below
   onFoot             (2),
   skateboard         (3),
   pushOrKickScooter  (4),
   wheelchair         (5), -- implies manually powered
   ...
}

PersonalAssistive::= BIT STRING {
   unavailable    (0),
   otherType      (1),
   vision         (2),
   hearing        (3),
   movement       (4),
   cognition      (5)
   } (SIZE (6, ...))

PersonalClusterRadius ::= INTEGER (0..100) -- units of meters

PersonalCrossingInProgress ::= BOOLEAN -- Use:
   -- True  = Yes, is in maneuver
   -- False = No

PersonalCrossingRequest ::= BOOLEAN
   -- Use:
   -- True  = On  (request crossing)
   -- False = Off (no request)

PersonalDeviceUsageState ::= BIT STRING {
   unavailable      (0), -- Not specified
   other            (1), -- Used for states not defined below
   idle             (2), -- Human is not interacting with device
   listeningToAudio (3), -- Any audio source other then calling
   typing           (4), -- Including texting, entering addresses
                         -- and other manual input activity
   calling          (5),
   playingGames     (6),
   reading          (7),
   viewing          (8)  -- Watching dynamic content, including following
                         -- navigation prompts, viewing videos or other
                         -- visual contents that are not static
   } (SIZE (9, ...))
   -- All bits shall be set to zero when unknown state

PersonalDeviceUserType ::= ENUMERATED {
   unavailable           (0),
   aPEDESTRIAN           (1), -- Further details may be provided elsewhere
   aPEDALCYCLIST         (2), -- Presumed to be human propelled,
                              -- unless PropelledInformation indicates motorized
   aPUBLICSAFETYWORKER   (3),
   anANIMAL              (4),
   ...
   }

PublicSafetyAndRoadWorkerActivity ::= BIT STRING {
   unavailable          (0), -- Not specified
   workingOnRoad        (1), -- Road workers on foot, in or out of
                             -- a closure, performing activities like:
                             -- construction, land surveying,
                             -- trash removal, or site inspection.
   settingUpClosures    (2), -- Road workers on foot performing
                             -- activities like: setting up signs,
                             -- placing cones/barrels/pylons, or placing
                             -- flares.  Note: People are in the road
                             -- redirecting traffic, but the closure is
                             -- not complete, so utmost care is required
                             -- to determine the allowed path to take to
                             -- avoid entering the work zone and/or
                             -- harming the workers.
   respondingToEvents   (3), -- Public safety or other road workers on
                             -- foot performing activities like: treating
                             -- injured people, putting out fires,
                             -- cleaning chemical spills, aiding disabled
                             -- vehicles, criminal investigations,
                             -- or animal control.  Note: These events tend
                             -- to be more dynamic than workingOnRoad
   directingTraffic     (4), -- Public safety or other road workers on
                             -- foot directing traffic in situations like:
                             -- a traffic signal out of operation,
                             -- a construction or crash site with a short
                             -- term lane closure, a single lane flagging
                             -- operation, or ingress/egress to a special event.
   otherActivities      (5)  -- Designated by regional authorities
   } (SIZE (6, ...))

PublicSafetyDirectingTrafficSubType ::= BIT STRING {
   unavailable                        (0),
      -- Default.
      -- to be used if unknown or if the worker type is not otherwise identified
   policeAndTrafficOfficers           (1),
      -- Law enforcement officers, including traffic control officers,
      -- and adult school crossing guards.
   trafficControlPersons              (2),
     -- Road workers with special equipment for directing traffic.
   railroadCrossingGuards             (3),
     -- Railroad crossing guards who notify motorists of approaching trains
     -- at locations like private roads or driveways crossing train tracks
     -- and where automated equipment is disabled or not present.
   civilDefenseNationalGuardMilitaryPolice (4),
        -- while performing their regular duties or during National
     -- or local emergencies
   emergencyOrganizationPersonnel     (5),
      -- Personnel belonging to emergency response organizations such as
      -- fire departments, hospitals, river rescue, or associated with
      -- emergency vehicles including ambulances as designated by the
      -- regional authority (relating to designation of emergency vehicles)
      -- while performing their duties.
   highwayServiceVehiclePersonnel     (6)
      -- Associated with tow trucks and road service vehicles.
   } (SIZE (7, ...))

PublicSafetyEventResponderWorkerType ::= ENUMERATED {
   unavailable               (0),
   towOperater               (1),
   fireAndEMSWorker          (2),
   aDOTWorker                (3),
   lawEnforcement            (4),
   hazmatResponder           (5), -- also any toxicSubstanceCleanupCrew
   animalControlWorker       (6),
   otherPersonnel            (7),
   ...
   }

UserSizeAndBehaviour ::= BIT STRING {
   unavailable                     (0),
   smallStature                    (1), -- less than 150 cm high
   largeStature                    (2),
   erraticMoving                   (3),
   slowMoving                      (4)  -- those who move a bit slowly
   } (SIZE (5, ...))
END

-- Use of this module defined in SAE J2735
-- Latest document release for this module is Nov 2022
-- Filename: J2735-ProbeDataManagement-2024-rel-v1.1.asn
--

ProbeDataManagement
{joint-iso-itu-t (2) country (16) us (840) organization (1) sae (114566)
v2x-communications (1) technical-committees (1) v2x-core (5) technical-reports (1)
j2735 (2735) part-0 (0) asn1-module (1) probeDataManagement (14)
version-1 (1) version-minor-1 (1)}

DEFINITIONS AUTOMATIC TAGS ::=
BEGIN

IMPORTS
   Reg-ProbeDataManagement
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   HeadingSlice,
   RegionalExtension,
   GrossSpeed
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





ProbeDataManagement ::= SEQUENCE {
   timeStamp            MinuteOfTheYear OPTIONAL,
   sample               Sample,           -- Identifies the vehicle
                                          -- population affected by this
   directions           HeadingSlice,     -- Applicable headings/directions
   term CHOICE {
      termtime          TermTime,         -- Terminate this management process
                                          -- based on Time-to-Live
      termDistance      TermDistance      -- Terminate management process
                                          -- based on Distance-to-Live
      },
   snapshot CHOICE {
      snapshotTime      SnapshotTime,     -- Collect snapshots based on Time
                                          -- the value 0 indicates forever
      snapshotDistance  SnapshotDistance  -- Collect snapshots based on combination
                                          -- of vehicle Speed and Distance
      },
   txInterval           SecondOfTime,     -- Time Interval at which to send snapshots
   dataElements         VehicleStatusRequestList OPTIONAL,
                                          -- Control data frames and associated
                                          -- trigger thresholds to be changed
   regional             SEQUENCE (SIZE(1..4)) OF
                        RegionalExtension {{Reg-ProbeDataManagement}} OPTIONAL,
   ...
   }

Sample ::= SEQUENCE {
   sampleStart  INTEGER(0..255),   --  Sample Starting Point
   sampleEnd    INTEGER(0..255)    --  Sample Ending Point
   }


SnapshotDistance ::= SEQUENCE {
   distance1   GrossDistance,   -- meters
   speed1      GrossSpeed,      -- meters/second
   distance2   GrossDistance,   -- meters
   speed2      GrossSpeed       -- meters/second
   }


SnapshotTime ::= SEQUENCE {
   speed1  GrossSpeed,     -- meters/sec - the instantaneous speed
                           -- when the calculation is performed
   time1   SecondOfTime,   -- in seconds
   speed2  GrossSpeed,     -- meters/sec - the instantaneous speed
                           -- when the calculation is performed
   time2   SecondOfTime    -- in seconds
   }


VehicleStatusRequest ::= SEQUENCE {
   dataType             VehicleStatusDeviceTypeTag,
   subType              INTEGER (1..15)   OPTIONAL,
   sendOnLessThenValue  INTEGER (-32767..32767) OPTIONAL,
   sendOnMoreThenValue  INTEGER (-32767..32767) OPTIONAL,
   sendAll              BOOLEAN OPTIONAL,
   ...
   }


VehicleStatusRequestList ::= SEQUENCE (SIZE(1..32)) OF VehicleStatusRequest

GrossDistance ::= INTEGER (0..1023) -- Units of 1.00 meters
   -- The value 1023 shall indicate unavailable

SecondOfTime ::= INTEGER (0..61)  -- units of seconds
    -- The value 60 shall be used for leap seconds
    -- or to indicate a full minute.
    -- The value 61 indicates that the value is unavailable

TermDistance ::= INTEGER (1..30000)   -- units in meters

TermTime ::= INTEGER (1..1800) -- units of sec

VehicleStatusDeviceTypeTag ::= ENUMERATED {
   unknown            (0),
   lights             (1),  -- Exterior Lights
   wipers             (2),  -- Wipers
   brakes             (3),  -- Brake Applied
   stab               (4),  -- Stability Control
   trac               (5),  -- Traction Control
   abs                (6),  -- Anti-Lock Brakes
   sunS               (7),  -- Sun Sensor
   rainS              (8),  -- Rain Sensor
   airTemp            (9),  -- Air Temperature
   steering           (10),
   vertAccelThres     (11), -- Wheel that Exceeded the
   vertAccel          (12), -- Vertical g Force Value
   hozAccelLong       (13), -- Longitudinal Acceleration
   hozAccelLat        (14), -- Lateral Acceleration
   hozAccelCon        (15), -- Acceleration Confidence
   accel4way          (16),
   confidenceSet      (17),
   obDist             (18), -- Obstacle Distance
   obDirect           (19), -- Obstacle Direction
   yaw                (20), -- Yaw Rate
   yawRateCon         (21), -- Yaw Rate Confidence
   dateTime           (22), -- complete time
   fullPos            (23), -- complete set of time and
                            -- position, speed, heading
   position2D         (24), -- lat, long
   position3D         (25), -- lat, long, elevation
   vehicle            (26), -- height, mass, type
   speedHeadC         (27),
   speedC             (28),

   ...
   }
END

-- Use of this module defined in SAE J2735
-- Latest document release for this module is Nov 2022
-- Filename: J2735-ProbeVehicleData-2024-rel-v1.1.asn
--

ProbeVehicleData
{joint-iso-itu-t (2) country (16) us (840) organization (1) sae (114566)
v2x-communications (1) technical-committees (1) v2x-core (5) technical-reports (1)
j2735 (2735) part-0 (0) asn1-module (1) probeVehicleData (15)
version-1 (1) version-minor-1 (1)}

DEFINITIONS AUTOMATIC TAGS ::=
BEGIN

IMPORTS
   Reg-ProbeVehicleData
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   EssPrecipYesNo,
   EssPrecipRate,
   EssPrecipSituation,
   EssSolarRadiation,
   EssMobileFriction
      FROM NTCIP {joint-iso-itu-t (2) country (16) us (840) organization (1) sae (114566)
      v2x-communications (1) technical-committees (1) v2x-core (5) technical-reports (1)
      j2735 (2735) part-0 (0) asn1-module (1) ntcip (5)
      version-1 (1) version-minor-1 (1)}
   ITISVehicleGroupAffected,
   ITISResponderGroupAffected,
   ITISIncidentResponseEquipment
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)}
   MinuteOfTheYear,
   FullPositionVector,
   VehicleClassification,
   RegionalExtension,
   SpeedandHeadingandThrottleConfidence,
   TimeConfidence,
   PositionConfidenceSet,
   HeadingConfidence,
   ThrottleConfidence,
   TrailerWeight,
   VehicleSafetyExtensions,
   DescriptiveName,
   VehicleID,
   VehicleType,
   ExteriorLights,
   LightbarInUse,
   WiperSet,
   BrakeSystemStatus,
   CoefficientOfFriction,
   AmbientAirTemperature,
   AmbientAirPressure,
   SteeringWheelAngle,
   AccelerationSet4Way,
   VerticalAccelerationThreshold,
   ObstacleDistance,
   Angle,
   DDateTime,
   SpeedConfidence,
   VehicleHeight,
   BumperHeights,
   VehicleMass,
   GNSSstatus
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





ProbeVehicleData ::= SEQUENCE {
   timeStamp       MinuteOfTheYear OPTIONAL,
   segNum          ProbeSegmentNumber OPTIONAL,
                                         -- a short term Ident value
                                         -- not used when ident is used
   probeID         VehicleIdent OPTIONAL,
                                         -- identity data for selected
                                         -- types of vehicles
   startVector     FullPositionVector,   -- the space and time of
                                         -- transmission to the RSU
   vehicleType     VehicleClassification, -- type of vehicle,
   snapshots       SEQUENCE (SIZE(1..32)) OF Snapshot,
                                         -- a seq of name-value pairs
                                         -- along with the space and time
                                         -- of the first measurement set
   regional        SEQUENCE (SIZE(1..4)) OF
                   RegionalExtension {{Reg-ProbeVehicleData}} OPTIONAL,
   ...
   }


AccelSteerYawRateConfidence ::= SEQUENCE {
   yawRate             YawRateConfidence,
   acceleration        AccelerationConfidence,
   steeringWheelAngle  SteeringWheelAngleConfidence
   }


ConfidenceSet ::= SEQUENCE {
   accelConfidence      AccelSteerYawRateConfidence OPTIONAL,
   speedConfidence      SpeedandHeadingandThrottleConfidence OPTIONAL,
   timeConfidence       TimeConfidence OPTIONAL,
   posConfidence        PositionConfidenceSet OPTIONAL,
   steerConfidence      SteeringWheelAngleConfidence OPTIONAL,
   headingConfidence    HeadingConfidence OPTIONAL,
   throttleConfidence   ThrottleConfidence OPTIONAL,
   ...
   }


J1939data ::= SEQUENCE {
   -- Tire conditions by tire
   tires                    TireDataList              OPTIONAL,
   -- Vehicle Weights by axle
   axles                    AxleWeightList            OPTIONAL,
   trailerWeight            TrailerWeight             OPTIONAL,
   cargoWeight              CargoWeight               OPTIONAL,
   steeringAxleTemperature  SteeringAxleTemperature   OPTIONAL,
   driveAxleLocation        DriveAxleLocation         OPTIONAL,
   driveAxleLiftAirPressure DriveAxleLiftAirPressure  OPTIONAL,
   driveAxleTemperature     DriveAxleTemperature      OPTIONAL,
   driveAxleLubePressure    DriveAxleLubePressure     OPTIONAL,
   steeringAxleLubePressure SteeringAxleLubePressure  OPTIONAL,
   ...
   }


TireDataList ::= SEQUENCE (SIZE(1..16)) OF TireData


TireData ::= SEQUENCE {
      location              TireLocation              OPTIONAL,
      pressure              TirePressure              OPTIONAL,
      temp                  TireTemp                  OPTIONAL,
      wheelSensorStatus     WheelSensorStatus         OPTIONAL,
      wheelEndElectFault    WheelEndElectFault        OPTIONAL,
      leakageRate           TireLeakageRate           OPTIONAL,
      detection             TirePressureThresholdDetection OPTIONAL,
      ...
      }

AxleWeightList ::= SEQUENCE (SIZE(1..16)) OF AxleWeightSet

AxleWeightSet ::= SEQUENCE {
      location              AxleLocation              OPTIONAL,
      weight                AxleWeight                OPTIONAL,
      ...
      }


Snapshot ::= SEQUENCE {
   thePosition  FullPositionVector,
                -- data of the position and speed,
   safetyExt    VehicleSafetyExtensions OPTIONAL,
   dataSet      VehicleStatus           OPTIONAL,
                -- a sequence of data frames
                -- which encodes the data
   ...
   }


VehicleIdent ::= SEQUENCE {
   name           DescriptiveName OPTIONAL,
                  -- a human readable name for debugging use
   vin            VINstring OPTIONAL,
                  -- vehicle VIN value
   ownerCode      IA5String(SIZE(1..32)) OPTIONAL,
                  -- vehicle owner code
   id             VehicleID OPTIONAL,
                  -- same value used in the BSM

   vehicleType    VehicleType  OPTIONAL,
   vehicleClass   CHOICE {
                     vGroup   ITISVehicleGroupAffected,
                     rGroup   ITISResponderGroupAffected,
                     rEquip   ITISIncidentResponseEquipment
                  } OPTIONAL,
   ...
   }


VehicleStatus ::= SEQUENCE {
   lights          ExteriorLights OPTIONAL,                 -- Exterior Lights
   lightBar        LightbarInUse  OPTIONAL,                 -- PS Lights

   wipers          WiperSet OPTIONAL,                      -- Wipers

   brakeStatus     BrakeSystemStatus OPTIONAL,
                                                            -- Braking Data
   brakePressure   BrakeAppliedPressure  OPTIONAL,          -- Braking Pressure
   roadFriction    CoefficientOfFriction OPTIONAL,          -- Roadway Friction


   sunData         SunSensor             OPTIONAL,          -- Sun Sensor
   rainData        RainSensor            OPTIONAL,          -- Rain Sensor
   airTemp         AmbientAirTemperature OPTIONAL,          -- Air Temperature
   airPres         AmbientAirPressure    OPTIONAL,          -- Air Pressure

   steering   SEQUENCE {
         angle      SteeringWheelAngle,
         confidence SteeringWheelAngleConfidence   OPTIONAL,
         rate       SteeringWheelAngleRateOfChange OPTIONAL,
         wheels     DrivingWheelAngle              OPTIONAL
         } OPTIONAL,                               -- steering data

   accelSets  SEQUENCE {
         accel4way       AccelerationSet4Way           OPTIONAL,
         vertAccelThres  VerticalAccelerationThreshold OPTIONAL,
                                                   -- Wheel which has
                                                   -- exceeded acceleration point
         yawRateCon      YawRateConfidence             OPTIONAL,
                                                   -- Yaw Rate Confidence
         hozAccelCon     AccelerationConfidence        OPTIONAL,
                                                   -- Acceleration Confidence
         confidenceSet   ConfidenceSet                 OPTIONAL
                                                   -- general ConfidenceSet
         } OPTIONAL,


   object     SEQUENCE {
         obDist          ObstacleDistance,          -- Obstacle Distance
         obDirect        Angle,                     -- Obstacle Direction
         dateTime        DDateTime                  -- time detected
         } OPTIONAL,                                -- detected Obstacle data



   fullPos         FullPositionVector OPTIONAL,     -- complete set of time and
                                                    -- position, speed, heading
   throttlePos     ThrottlePosition OPTIONAL,
   speedHeadC      SpeedandHeadingandThrottleConfidence OPTIONAL,
   speedC          SpeedConfidence OPTIONAL,

   vehicleData   SEQUENCE {
         height        VehicleHeight,
         bumpers       BumperHeights,
         mass          VehicleMass,
         trailerWeight TrailerWeight,
         type          VehicleType
         -- values for width and length are sent in BSM part I as well.
         } OPTIONAL,                            -- vehicle data

   vehicleIdent   VehicleIdent OPTIONAL,        -- common vehicle identity data

   j1939data      J1939data OPTIONAL,           -- Various SAE J1938 data items

   weatherReport SEQUENCE {
         isRaining        EssPrecipYesNo,
         rainRate         EssPrecipRate       OPTIONAL,
         precipSituation  EssPrecipSituation  OPTIONAL,
         solarRadiation   EssSolarRadiation   OPTIONAL,
         friction         EssMobileFriction   OPTIONAL
         } OPTIONAL,                                        -- local weather data

   gnssStatus      GNSSstatus          OPTIONAL,              -- vehicle's GPS

   ...
   }

AccelerationConfidence ::= ENUMERATED {
   unavailable  (0), -- Not Equipped or data is unavailable
   accl-100-00  (1), -- 100  meters / second squared
   accl-010-00  (2), -- 10   meters / second squared
   accl-005-00  (3), -- 5    meters / second squared
   accl-001-00  (4), -- 1    meters / second squared
   accl-000-10  (5), -- 0.1  meters / second squared
   accl-000-05  (6), -- 0.05 meters / second squared
   accl-000-01  (7)  -- 0.01 meters / second squared
   } -- Encoded as a 3 bit value

BrakeAppliedPressure ::= ENUMERATED {
   unavailable  (0),  -- B'0000 Not Equipped
                      -- or Brake Pres status is unavailable
   minPressure  (1),  -- B'0001 Minimum Braking Pressure
   bkLvl-2      (2),  -- B'0010
   bkLvl-3      (3),  -- B'0011
   bkLvl-4      (4),  -- B'0100
   bkLvl-5      (5),  -- B'0101
   bkLvl-6      (6),  -- B'0110
   bkLvl-7      (7),  -- B'0111
   bkLvl-8      (8),  -- B'1000
   bkLvl-9      (9),  -- B'1001
   bkLvl-10     (10), -- B'1010
   bkLvl-11     (11), -- B'1011
   bkLvl-12     (12), -- B'1100
   bkLvl-13     (13), -- B'1101
   bkLvl-14     (14), -- B'1110
   maxPressure  (15)  -- B'1111 Maximum Braking Pressure
   }  -- Encoded as a 4 bit value

DrivingWheelAngle ::= INTEGER (-128..127)
   -- LSB units of 0.3333 degrees.
   -- a range of 42.33 degrees each way

AxleLocation ::= INTEGER (0..255)

AxleWeight ::= INTEGER (0..64255)

CargoWeight ::= INTEGER (0..64255)

DriveAxleLiftAirPressure ::= INTEGER (0..1000)

DriveAxleLocation ::= INTEGER (0..255)

DriveAxleLubePressure ::= INTEGER (0..250)

DriveAxleTemperature ::= INTEGER (-40..210)

SteeringAxleLubePressure ::= INTEGER (0..250)

SteeringAxleTemperature ::= INTEGER (-40..210)

TireLeakageRate ::= INTEGER (0..64255)

TireLocation ::= INTEGER (0..255)

TirePressureThresholdDetection ::= ENUMERATED {
   noData                (0),  -- B'000'
   overPressure          (1),  -- B'001'
   noWarningPressure     (2),  -- B'010'
   underPressure         (3),  -- B'011'
   extremeUnderPressure  (4),  -- B'100'
   undefined             (5),  -- B'101'
   errorIndicator        (6),  -- B'110'
   notAvailable          (7)   -- B'111'
   }  -- Encoded as a 3 bit value

TirePressure ::= INTEGER (0..250)

TireTemp ::= INTEGER (-8736..55519)

WheelEndElectFault ::= ENUMERATED {
   isOk            (0), -- No fault
   isNotDefined    (1),
   isError         (2),
   isNotSupported  (3)
   }

WheelSensorStatus ::= ENUMERATED {
   off           (0),
   on            (1),
   notDefined    (2),
   notSupported  (3)
   }

ProbeSegmentNumber ::= INTEGER (0..32767)
   -- value determined by local device
   -- as per standard

RainSensor ::= ENUMERATED {
     none               (0),
     lightMist          (1),
     heavyMist          (2),
     lightRainOrDrizzle (3),
     rain               (4),
     moderateRain       (5),
     heavyRain          (6),
     heavyDownpour      (7)
     }

SteeringWheelAngleConfidence ::= ENUMERATED {
   unavailable (0), -- B'00  Not Equipped with Wheel angle
                    -- or Wheel angle status is unavailable
   prec2deg    (1), -- B'01  2 degrees
   prec1deg    (2), -- B'10  1 degree
   prec0-02deg (3)  -- B'11  0.02 degrees
   }

SteeringWheelAngleRateOfChange ::= INTEGER (-127..127)
   -- LSB is 3 degrees per second

SunSensor ::= INTEGER (0..1000)
   -- units of watts / m2

ThrottlePosition ::= INTEGER (0..200) -- LSB units are 0.5 percent

VINstring ::= OCTET STRING (SIZE(1..17))
   -- A legal VIN or a shorter value
   -- to provide an ident of the vehicle
   -- If a VIN is sent, then IA5 encoding
   -- shall be used

YawRateConfidence ::= ENUMERATED {
   unavailable    (0), -- B'000  Not Equipped with yaw rate status
                       -- or yaw rate status is unavailable
   degSec-100-00  (1), -- B'001  100  deg/sec
   degSec-010-00  (2), -- B'010  10   deg/sec
   degSec-005-00  (3), -- B'011  5    deg/sec
   degSec-001-00  (4), -- B'100  1    deg/sec
   degSec-000-10  (5), -- B'101  0.1  deg/sec
   degSec-000-05  (6), -- B'110  0.05 deg/sec
   degSec-000-01  (7)  -- B'111  0.01 deg/sec
   }
   -- Encoded as a 3 bit value
END

-- Use of this module defined in SAE J2735
-- Latest document release for this module is Nov 2022
-- Filename: J2735-REGION-2024-rel-v1.1.asn
--

REGION
{joint-iso-itu-t (2) country (16) us (840) organization (1) sae (114566)
v2x-communications (1) technical-committees (1) v2x-core (5) technical-reports (1)
j2735 (2735) part-0 (0) asn1-module (1) region (2) version-1 (1) version-minor-1 (1)}

DEFINITIONS AUTOMATIC TAGS ::=
BEGIN

IMPORTS
   ConnectionManeuverAssist-addGrpC,
   IntersectionState-addGrpC,
   Position3D-addGrpC,
   RestrictionUserType-addGrpC,
   MapData-addGrpC
      FROM AddGrpC {joint-iso-itu-t (2) country (16) us (840) organization (1) sae (114566)
      v2x-communications (1) technical-committees (1) v2x-core (5) technical-reports (1)
      j2735 (2735) part-0 (0) asn1-module (1) addgrpc (3)
      version-1 (1) version-minor-1 (1)}
   LaneDataAttribute-addGrpB,
   MovementEvent-addGrpB,
   NodeOffsetPointXY-addGrpB,
   Position3D-addGrpB
      FROM AddGrpB {joint-iso-itu-t (2) country (16) us (840) organization (1) sae (114566)
      v2x-communications (1) technical-committees (1) v2x-core (5) technical-reports (1)
      j2735 (2735) part-0 (0) asn1-module (1) addgrpb (4)
      version-1 (1) version-minor-1 (1)}
   REG-EXT-ID-AND-TYPE,
   addGrpC,
   addGrpB
      FROM Common {joint-iso-itu-t (2) country (16) us (840) organization (1) sae (114566)
      v2x-communications (1) technical-committees (1) v2x-core (5) technical-reports (1)
      j2735 (2735) part-0 (0) asn1-module (1) common (38)
      version-1 (1) version-minor-1 (1)};


-- -_-_-_-_-_-_-_-_-_-_-_-_-_-_-_-_-_-_-_-_-_-_-_-_-_-_-_-_
--
-- Start of entries from table Dialogs...
-- This table typically contains dialog and operational exchange entries.
-- -_-_-_-_-_-_-_-_-_-_-_-_-_-_-_-_-_-_-_-_-_-_-_-_-_-_-_-_


--
-- Regional data frames with no currently defined extensions
--
Reg-AdvisorySpeed         REG-EXT-ID-AND-TYPE ::= { ...  }
Reg-ComputedLane          REG-EXT-ID-AND-TYPE ::= { ...  }
Reg-EventDescription      REG-EXT-ID-AND-TYPE ::= { ...  }
Reg-GenericLane           REG-EXT-ID-AND-TYPE ::= { ...  }
Reg-GeographicalPath      REG-EXT-ID-AND-TYPE ::= { ...  }
Reg-GeometricProjection   REG-EXT-ID-AND-TYPE ::= { ...  }
Reg-IntersectionGeometry  REG-EXT-ID-AND-TYPE ::= { ...  }
Reg-LaneAttributes        REG-EXT-ID-AND-TYPE ::= { ...  }
Reg-MovementState         REG-EXT-ID-AND-TYPE ::= { ...  }
Reg-NodeAttributeSetLL    REG-EXT-ID-AND-TYPE ::= { ...  }
Reg-NodeAttributeSetXY    REG-EXT-ID-AND-TYPE ::= { ...  }
Reg-NodeOffsetPointLL     REG-EXT-ID-AND-TYPE ::= { ...  }
Reg-RequestorDescription  REG-EXT-ID-AND-TYPE ::= { ...  }
Reg-RequestorType         REG-EXT-ID-AND-TYPE ::= { ...  }
Reg-RoadSegment           REG-EXT-ID-AND-TYPE ::= { ...  }
Reg-SignalControlZone     REG-EXT-ID-AND-TYPE ::= { ...  }
Reg-SignalRequest         REG-EXT-ID-AND-TYPE ::= { ...  }
Reg-SignalRequestPackage  REG-EXT-ID-AND-TYPE ::= { ...  }
Reg-SignalStatus          REG-EXT-ID-AND-TYPE ::= { ...  }
Reg-SignalStatusPackage   REG-EXT-ID-AND-TYPE ::= { ...  }
Reg-SupplementalVehicleExtensions REG-EXT-ID-AND-TYPE ::= { ...  }
Reg-VehicleClassification REG-EXT-ID-AND-TYPE ::= { ...  }
Reg-VerticalOffset        REG-EXT-ID-AND-TYPE ::= { ...  }

--
-- Data Frames with current adopted expansion point content
--
Reg-ConnectionManeuverAssist REG-EXT-ID-AND-TYPE ::= {
   { ConnectionManeuverAssist-addGrpC IDENTIFIED BY addGrpC} ,
   ...
   }

Reg-IntersectionState     REG-EXT-ID-AND-TYPE ::= {
   { IntersectionState-addGrpC IDENTIFIED BY addGrpC} ,
   ...
   }

Reg-LaneDataAttribute     REG-EXT-ID-AND-TYPE ::= {
   { LaneDataAttribute-addGrpB IDENTIFIED BY addGrpB} ,
   ...
   }

Reg-MovementEvent         REG-EXT-ID-AND-TYPE ::= {
   { MovementEvent-addGrpB IDENTIFIED BY addGrpB} ,
   ...
   }

Reg-NodeOffsetPointXY     REG-EXT-ID-AND-TYPE ::= {
   { NodeOffsetPointXY-addGrpB IDENTIFIED BY addGrpB} ,
   ...
   }

Reg-Position3D            REG-EXT-ID-AND-TYPE ::= {
   { Position3D-addGrpB IDENTIFIED BY addGrpB} |
   { Position3D-addGrpC IDENTIFIED BY addGrpC} ,
   ...
   }

Reg-RestrictionUserType   REG-EXT-ID-AND-TYPE ::= {
   { RestrictionUserType-addGrpC IDENTIFIED BY addGrpC} ,
   ...
   }



--
-- The pattern used for regional adaptations is shown below
-- Use:
-- the text 'XXX' below is used to represent the name of the entry
-- the region should replace 'xxx-RegionName' with its own Type Def
-- a name pattern such as 'DataFrameName-RegionName' is recommended
-- the 'regionName' value must be assigned from the RegionId element
-- this value would be defined in the REGION module, unless a well-known
-- region was being used (these IDs are defined in the V2X module)
-- refer to the full standard for additional details
--
--Reg-XXX DSRC.REG-EXT-ID-AND-TYPE ::= {
--   { XXX-RegionName IDENTIFIED BY regionName  },
--   ...
--}
--regionName DSRC.RegionId ::= 128
--XXX-RegionName ::= SEQUENCE { ... }
--
-- End example pattern for regional use


-- Extension markers for operational messages in the standard
-- Messages with no currently defined extensions
Reg-BasicSafetyMessage     REG-EXT-ID-AND-TYPE ::= { ... }
Reg-CommonSafetyRequest    REG-EXT-ID-AND-TYPE ::= { ... }
Reg-EmergencyVehicleAlert  REG-EXT-ID-AND-TYPE ::= { ... }
Reg-IntersectionCollision  REG-EXT-ID-AND-TYPE ::= { ... }
Reg-NMEAcorrections        REG-EXT-ID-AND-TYPE ::= { ... }
Reg-ProbeDataManagement    REG-EXT-ID-AND-TYPE ::= { ... }
Reg-ProbeVehicleData       REG-EXT-ID-AND-TYPE ::= { ... }
Reg-RoadSideAlert          REG-EXT-ID-AND-TYPE ::= { ... }
Reg-RTCMcorrections        REG-EXT-ID-AND-TYPE ::= { ... }
Reg-SignalRequestMessage   REG-EXT-ID-AND-TYPE ::= { ... }
Reg-SignalStatusMessage    REG-EXT-ID-AND-TYPE ::= { ... }
Reg-SPAT                   REG-EXT-ID-AND-TYPE ::= { ... }
Reg-TravelerInformation    REG-EXT-ID-AND-TYPE ::= { ... }
Reg-PersonalSafetyMessage  REG-EXT-ID-AND-TYPE ::= { ... }

-- Messages with current adopted extension marker content
Reg-MapData                REG-EXT-ID-AND-TYPE ::= {
   { MapData-addGrpC IDENTIFIED BY addGrpC},
   ...
   }


-- Test Messages
Reg-TestMessage00    REG-EXT-ID-AND-TYPE ::= { ... }
Reg-TestMessage01    REG-EXT-ID-AND-TYPE ::= { ... }
Reg-TestMessage02    REG-EXT-ID-AND-TYPE ::= { ... }
Reg-TestMessage03    REG-EXT-ID-AND-TYPE ::= { ... }
Reg-TestMessage04    REG-EXT-ID-AND-TYPE ::= { ... }
Reg-TestMessage05    REG-EXT-ID-AND-TYPE ::= { ... }
Reg-TestMessage06    REG-EXT-ID-AND-TYPE ::= { ... }
Reg-TestMessage07    REG-EXT-ID-AND-TYPE ::= { ... }
Reg-TestMessage08    REG-EXT-ID-AND-TYPE ::= { ... }
Reg-TestMessage09    REG-EXT-ID-AND-TYPE ::= { ... }
Reg-TestMessage10    REG-EXT-ID-AND-TYPE ::= { ... }
Reg-TestMessage11    REG-EXT-ID-AND-TYPE ::= { ... }
Reg-TestMessage12    REG-EXT-ID-AND-TYPE ::= { ... }
Reg-TestMessage13    REG-EXT-ID-AND-TYPE ::= { ... }
Reg-TestMessage14    REG-EXT-ID-AND-TYPE ::= { ... }
Reg-TestMessage15    REG-EXT-ID-AND-TYPE ::= { ... }
END

-- Use of this module defined in SAE J2735
-- Latest document release for this module is Nov 2022
-- Filename: J2735-AddGrpB-2024-rel-v1.1.asn
--

AddGrpB
{joint-iso-itu-t (2) country (16) us (840) organization (1) sae (114566)
v2x-communications (1) technical-committees (1) v2x-core (5) technical-reports (1)
j2735 (2735) part-0 (0) asn1-module (1) addgrpb (4) version-1 (1) version-minor-1 (1)}

DEFINITIONS AUTOMATIC TAGS ::=
BEGIN

IMPORTS
   TimeIntervalConfidence
      FROM SPAT {joint-iso-itu-t (2) country (16) us (840) organization (1) sae (114566)
      v2x-communications (1) technical-committees (1) v2x-core (5) technical-reports (1)
      j2735 (2735) part-0 (0) asn1-module (1) signalPhaseAndTimingMessage (9)
      version-1 (1) version-minor-1 (1)};

GrpBAngle ::= INTEGER (0..239)
   -- Unsigned units of 1.5 degree, in 1 octet
   -- the true north is 0, positive is clockwise
   -- the values 240 to 254 shall not be sent
   -- the value 255 (0xFF) indicates an invalid value

Day ::= INTEGER (0..255)
   -- BCD coding of Day of Month, in 1 octet
   -- values with nibble values between 1010 and 1111 shall not be sent
   -- except that the value xxx (0xFF shall indicate an invalid value

DayOfWeek ::= ENUMERATED {
    unknown   (0),
    monday    (1),
    tuesday   (2),
    wednesday (3),
    thursday  (4),
    friday    (5),
    saturday  (6),
    sunday    (7)
    }
   -- Encoding as per above, in 3 bits
   -- the value 0x00 shall indicate an invalid value

DegreesLat ::= INTEGER (-90..90)
   -- Signed units of degrees, in 1 octets
   -- the values  +91 to +126 shall not be sent
   -- the values -128 to  -91 shall not be sent
   -- the value 127 (0x7F) shall indicate an invalid value

DegreesLong ::= INTEGER (-180..180)
   -- Signed units of degrees, in 2 octets
   -- the values +181 to +32766 shall not be sent
   -- the values -181 to -32768 shall not be sent
   -- the value 32767 (0x7FFF shall indicate an invalid value

GrpBElevation ::= INTEGER (-32768..32767)
  -- Signed units of 0.1m (10cm), in 2 octets
  -- the value 32767 (0x7FFF) shall indicate an invalid value

Holiday ::= ENUMERATED {
    weekday  (0),
    holiday  (1)
    }
   -- Encoding as per above, in 1 bit

Hour ::= INTEGER (0..255)
   -- BCD coding of Hour of a Day, in 1 octet
   -- values above upper nibble 0010 and lower nibble 0100 shall not be sent
   -- values with lower nibble values between 1010 and 1111 shall not be sent
   -- except that the value 255 (0xFF) shall indicate an invalid value

LatitudeDMS ::= INTEGER (-32400000.. 32400000)
   -- Signed units of 0.01 seconds of a minute of a degree of Latitude
   -- Providing a range of plus-minus 90 degrees
   -- in a 4 octet value when implicit or in BER forms
   -- the value 0x7FFF FFFF shall indicate an invalid value

LongitudeDMS ::= INTEGER (-64800000.. 64800000)
   -- Signed units of 0.01 seconds of a minute of a degree of Longitude
   -- Providing a range of plus-minus 180 degrees
   -- in a 4 octet value when implicit or in BER forms
   -- the value 0x7FFF FFFF shall indicate an invalid value

MaxTimetoChange ::= INTEGER (0..2402)
   -- Unsigned units of 0.1 seconds, in 2 octets
   -- the value 2401 shall indicate 'forever'
   -- the values 2402 to 65534 shall not be sent
   -- the value 65535 (0xFFFF) shall indicate an invalid value

MinTimetoChange ::= INTEGER (0..2402)
   -- Unsigned units of 0.1 seconds, in 2 octets
   -- the value 2401 shall indicate 'forever'
   -- the values 2402 to 32766 shall not be sent
   -- the value 32767(0x7FFF) shall indicate an invalid value
   -- Note that:
   -- The MSB is used as a flag and set to one to
   -- indicate that the value does not count down.
   -- Under this condition the movement phase may end
   -- immediately if certain condition are meet.

Minute ::= INTEGER (0..255)
   -- BCD coding of Minute of an Hour, in 1 octet
   -- values above a combined BCD value of 59 (>59)
   -- (i.e., 0110 0000) shall not be sent
   -- except that value 255 (0xFF) shall indicate an invalid value

MinutesAngle ::= INTEGER (0..59)
   -- Unsigned units of minutes of an angle, in 1 octet
   -- values above 59 shall not be sent
   -- except that value 255 (0xFF) shall indicate an invalid value

Month ::= INTEGER (1..255)
   -- BCD coding of Month of a year, in 1 octet
   -- values above a combined BCD value of 12 (>12)
   -- (i.e., 0001 0011) shall not be sent
   -- except that value 255 (0xFF) shall indicate an invalid value

GrpBMsgCount ::= INTEGER (0..255)
   -- a count value which is incremented with each use
   -- the next value after 255 shall be one
   -- value 0 (0x00) shall indicate that MsgCount is not available

Second ::= INTEGER (0..60)
   -- BCD coding of a second of time, in 1 octet
   -- values above a combined BCD value of 60
   -- (i.e., 0110 0000) shall not be sent
   -- except that value 255 (0xFF) shall indicate an invalid value

SecondsAngle ::= INTEGER (0..5999)
   -- Unsigned units of 1/100th seconds of angle, in 2 octets
   -- values from 6000 to 65534 shall not be sent
   -- the value 65535 (0xFFFF) shall indicate an invalid value

SummerTime ::= ENUMERATED {
    notInSummerTime   (0),
    inSummerTime      (1)
    }
   -- Encoding as per above, in 1 bit

TenthSecond ::= INTEGER (0..9)
   -- Unsigned units of 100 milliseconds, in 1 octet
   -- values from 10 to 254 shall not be sent
   -- the value 255 (0xFF) shall indicate an invalid value

TimeRemaining ::= INTEGER (0..9001)
    -- Unsigned units of 0.1 seconds, spanning 15 minutes, in 2 octets
    -- the value 9001 shall indicate 'forever'
    -- values from 9002 to 65534 shall not be sent
    -- the value 65535 (0xFFFF) shall indicate an invalid value

Year ::= INTEGER (1..65535)
   -- BCD coding of four digits of the year A.D. in 2 octets
   -- values with nibble values between 1010 and 1111 shall not be sent
   -- except that the value 65535 (0xFFFF) shall indicate an invalid value

LatitudeDMS2 ::= SEQUENCE {
   d  DegreesLat,    -- units of degrees
   m  MinutesAngle,  -- units of minutes
   s  SecondsAngle   -- units of 1/100th seconds
   } -- total size of 4 octets (32 bits) when implicit encoding is used

LongitudeDMS2 ::= SEQUENCE {
   d  DegreesLong,   -- units of degrees
   m  MinutesAngle,  -- units of minutes
   s  SecondsAngle   -- units of 1/100th seconds
   } -- total size of 5 octets (40 bits) when implicit encoding is used

Node-LLdms-48b ::= SEQUENCE {
   lon  LongitudeDMS,
   lat  LatitudeDMS
   }

Node-LLdms-80b ::= SEQUENCE {
   lon  LongitudeDMS2,
   lat  LatitudeDMS2
   }

LaneDataAttribute-addGrpB ::= SEQUENCE { ... }

MovementEvent-addGrpB ::= SEQUENCE {
   -- A set of countdown style time-to-change values
   -- all in units of 0.1 seconds and following
   -- the naming of the base V2X standard

   startTime   TimeRemaining   OPTIONAL,
               -- When this phase 1st started
   minEndTime  MinTimetoChange,
               -- Expected shortest end time
   maxEndTime  MaxTimetoChange OPTIONAL,
               -- Expected longest end time
   likelyTime  TimeRemaining   OPTIONAL,
               -- Best predicted value based on other data
   confidence  TimeIntervalConfidence   OPTIONAL,
               -- Applies to above time element only
   nextTime    TimeRemaining   OPTIONAL,
   ...
   }

NodeOffsetPointXY-addGrpB ::= CHOICE {
   -- Full position expressed in units of 0.01 seconds
   posA    Node-LLdms-48b,

   -- Full position expressed in multiple elements in
   -- an DD.MM.SS.sss style format
   posB    Node-LLdms-80b,

   ...
   }

Position3D-addGrpB ::= SEQUENCE {
   latitude     LatitudeDMS2,
   longitude    LongitudeDMS2,
   elevation    GrpBElevation,
   ...
   }

GrpBTimeMark ::= SEQUENCE {
    year        Year,         -- BCD coding of A.D.    2 octets
    month       Month,        -- BCD coding of Month,  1 octet
    day         Day,          -- BCD coding of Day,    1 octet
    summerTime  SummerTime,
    holiday     Holiday,
    dayofWeek   DayOfWeek,
    hour        Hour,         -- BCD coding of Hour,   1 octet
    minute      Minute,       -- BCD coding of Minute, 1 octet
    second      Second,       -- BCD coding of Second, 1 octet
    tenthSecond TenthSecond   -- units of 100 millisecond, 1 octet
}

END

-- Use of this module defined in SAE J2735
-- Latest document release for this module is Nov 2022
-- Filename: J2735-AddGrpC-2024-rel-v1.1.asn
--

AddGrpC
{joint-iso-itu-t (2) country (16) us (840) organization (1) sae (114566)
v2x-communications (1) technical-committees (1) v2x-core (5) technical-reports (1)
j2735 (2735) part-0 (0) asn1-module (1) addgrpc (3) version-1 (1)
version-minor-1 (1)}
DEFINITIONS AUTOMATIC TAGS ::=
BEGIN

IMPORTS
   StationID,
   PrioritizationResponseStatus,
   SignalGroupID,
   NodeOffsetPointXY,
   LaneID
      FROM Common {joint-iso-itu-t (2) country (16) us (840) organization (1) sae (114566)
      v2x-communications (1) technical-committees (1) v2x-core (5) technical-reports (1)
      j2735 (2735) part-0 (0) asn1-module (1) common (38)
      version-1 (1) version-minor-1 (1)};


AltitudeConfidence ::= ENUMERATED {
   alt-000-01,  -- accuracy within    0.01 meter
   alt-000-02,  -- accuracy within    0.02 meter
   alt-000-05,  -- accuracy within    0.05 meter
   alt-000-10,  -- accuracy within    0.10 meter
   alt-000-20,  -- accuracy within    0.20 meter
   alt-000-50,  -- accuracy within    0.50 meter
   alt-001-00,  -- accuracy within    1.00 meter
   alt-002-00,  -- accuracy within    2.00 meter
   alt-005-00,  -- accuracy within    5.00 meter
   alt-010-00,  -- accuracy within   10.00 meter
   alt-020-00,  -- accuracy within   20.00 meter
   alt-050-00,  -- accuracy within   50.00 meter
   alt-100-00,  -- accuracy within  100.00 meter
   alt-200-00,  -- accuracy within  200.00 meter
   outOfRange,  -- accuracy exceeds 200.00 meters
   unavailable  -- unavailable
}

AltitudeValue ::= INTEGER (-100000..800001)  -- units of  0.01 meter
   -- Where:
   -- seaLevel(0),
   -- oneCentimeter(1),
   -- unavailable(800001)

EmissionType ::= ENUMERATED {
     typeA,  -- check for proper restrictions
     typeB,  --
     typeC,  --
     typeD,  --
     typeE,  --
     ...
     }

Altitude ::= SEQUENCE {
   value        AltitudeValue,
   confidence   AltitudeConfidence
   }

PrioritizationResponse ::= SEQUENCE {
   stationID      StationID,
                  -- Id of requesting vehicle
                  -- Note that the stationID has to remain unchanged
                  -- during the whole prioritizationprocess
   priorState     PrioritizationResponseStatus,
                  -- State of prioritization request
   signalGroup    SignalGroupID,
                  -- id of prioritized LaneSet, which will
                  -- be given free way
   ...
   }

PrioritizationResponseList ::= SEQUENCE SIZE(1..10) OF PrioritizationResponse

ConnectionManeuverAssist-addGrpC ::= SEQUENCE {
    vehicleToLanePositions  VehicleToLanePositionList,
    rsuDistanceFromAnchor   NodeOffsetPointXY OPTIONAL
}

IntersectionState-addGrpC ::= SEQUENCE {
   activePrioritizations PrioritizationResponseList OPTIONAL,
   ... }

MapData-addGrpC ::= SEQUENCE {
   signalHeadLocations   SignalHeadLocationList OPTIONAL,
   ...
   }

Position3D-addGrpC ::= SEQUENCE {
   altitude    Altitude,
   ...
   }

RestrictionUserType-addGrpC ::= SEQUENCE {
   emission   EmissionType OPTIONAL,
   ...
   }

SignalHeadLocation ::= SEQUENCE {
   node             NodeOffsetPointXY, -- the location
   signalGroupID    SignalGroupID,
   ...
}

SignalHeadLocationList ::= SEQUENCE (SIZE(1..20)) OF  SignalHeadLocation

VehicleToLanePosition ::= SEQUENCE {
    stationID   StationID,
    laneID      LaneID,
    ...
    }

VehicleToLanePositionList ::= SEQUENCE SIZE(1..5) OF VehicleToLanePosition
END

-- Use of this module defined in SAE J2735
-- Latest document release for this module is Nov 2022
-- Filename: J2735-RoadSideAlert-2024-rel-v1.1.asn
--

RoadSideAlert
{joint-iso-itu-t (2) country (16) us (840) organization (1) sae (114566)
v2x-communications (1) technical-committees (1) v2x-core (5) technical-reports (1)
j2735 (2735) part-0 (0) asn1-module (1) roadSideAlert (16) version-1 (1) version-minor-1 (1)}

DEFINITIONS AUTOMATIC TAGS ::=
BEGIN

IMPORTS
   Reg-RoadSideAlert
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   ITIScodes
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)}
   MsgCount,
   MinuteOfTheYear,
   Priority,
   HeadingSlice,
   Extent,
   FullPositionVector,
   FurtherInfoID,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





RoadSideAlert ::= SEQUENCE {
   msgCnt        MsgCount,
   timeStamp     MinuteOfTheYear  OPTIONAL,
   typeEvent     ITIScodes,
                 -- a category and an item from that category
                 -- all ITS stds use the same types here
                 -- to explain the type of  the
                 -- alert / danger / hazard involved
   description   SEQUENCE (SIZE(1..8)) OF ITIScodes OPTIONAL,
                 -- up to eight ITIS code set entries to further
                 -- describe the event, give advice, or any
                 -- other ITIS codes
   priority      Priority OPTIONAL,
                 -- the urgency of this message, a relative
                 -- degree of merit compared with other
                 -- similar messages for this type (not other
                 -- messages being sent by the device), nor a
                 -- priority of display urgency
   heading       HeadingSlice  OPTIONAL,
                 -- Applicable headings/direction
   extent        Extent OPTIONAL,
                 -- the spatial distance over which this
                 -- message applies and should be presented
                 -- to the driver
   position      FullPositionVector OPTIONAL,
                 -- a compact summary of the position,
                 -- heading, speed, etc. of the
                 -- event in question. Including stationary
                 -- and wide area events.
   furtherInfoID FurtherInfoID OPTIONAL,
                 -- an index link to any other incident
                 -- information data that may be available
                 -- in the normal ATIS incident description
                 -- or other messages
                 -- 1~2 octets in length
   regional      SEQUENCE (SIZE(1..4)) OF
                 RegionalExtension {{Reg-RoadSideAlert}} OPTIONAL,
   ...
   }
END

-- Use of this module defined in SAE J2735
-- Latest document release for this module is Nov 2022
-- Filename: J2735-RTCMcorrections-2024-rel-v1.1.asn
--

RTCMcorrections
{joint-iso-itu-t (2) country (16) us (840) organization (1) sae (114566)
v2x-communications (1) technical-committees (1) v2x-core (5) technical-reports (1)
j2735 (2735) part-0 (0) asn1-module (1) rtcmCorrections (17) version-1 (1) version-minor-1 (1)}

DEFINITIONS AUTOMATIC TAGS ::=
BEGIN

IMPORTS
   Reg-RTCMcorrections
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MsgCount,
   MinuteOfTheYear,
   FullPositionVector,
   RTCMheader,
   RTCMmessageList,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





RTCMcorrections ::= SEQUENCE {
   msgCnt      MsgCount,
   rev         RTCM-Revision,
               -- the specific edition of the standard
               -- that is being sent
   timeStamp   MinuteOfTheYear  OPTIONAL,

   -- Observer position, if needed
   anchorPoint FullPositionVector OPTIONAL,
   -- Precise ant position and noise data for a rover
   rtcmHeader  RTCMheader OPTIONAL,

   -- one or more RTCM messages
   msgs        RTCMmessageList,
   regional    SEQUENCE (SIZE(1..4)) OF
               RegionalExtension {{Reg-RTCMcorrections}} OPTIONAL,
   ...
   }

RTCM-Revision ::= ENUMERATED {
     unknown       (0),
     rtcmRev2      (1), -- Std 10402.x et al
     rtcmRev3      (2), -- Std 10403.x et al
     reserved      (3),
     ...
     }
END

-- Use of this module defined in SAE J2735
-- This standard is not released (WIP)
-- Filename: J2735-SCPR-2024-ph-v1.1.asn
--
-- Note: This is a *placeholder* file for the fully defined ASN.1 module.
-- Replace this file with the correct SAE file to compile a functional module.
--

SignalControlAndPrioritizationRequest
{joint-iso-itu-t (2) country (16) us (840) organization (1) sae (114566)
v2x-communications (1) technical-committees (1) v2x-core (5) technical-reports (1)
j2735 (2735) part-0 (0) asn1-module (1) signalControlAndPrioritizationRequest (46)
version-1 (1) version-minor-1 (1)}


DEFINITIONS AUTOMATIC TAGS ::=
BEGIN

SignalControlAndPrioritizationRequest ::= NULL

END-- Use of this module defined in SAE J2735
-- This standard is not released (WIP)
-- Filename: J2735-SCPS-2024-ph-v1.1.asn
--
-- Note: This is a *placeholder* file for the fully defined ASN.1 module.
-- Replace this file with the correct SAE file to compile a functional module.
--

SignalControlAndPrioritizationStatus
{joint-iso-itu-t (2) country (16) us (840) organization (1) sae (114566)
v2x-communications (1) technical-committees (1) v2x-core (5) technical-reports (1)
j2735 (2735) part-0 (0) asn1-module (1) signalControlAndPrioritizationStatus (47)
version-1 (1) version-minor-1 (1)}


DEFINITIONS AUTOMATIC TAGS ::=
BEGIN

SignalControlAndPrioritizationStatus ::= NULL

END-- Use of this module defined in SAE J2735
-- Latest document release for this module is Nov 2022
-- Filename: J2735-SignalRequestMessage-2024-rel-v1.1.asn
--

SignalRequestMessage
{joint-iso-itu-t (2) country (16) us (840) organization (1) sae (114566)
v2x-communications (1) technical-committees (1) v2x-core (5) technical-reports (1)
j2735 (2735) part-0 (0) asn1-module (1) signalRequestMessage (18) version-1 (1) version-minor-1 (1)}

DEFINITIONS AUTOMATIC TAGS ::=
BEGIN

IMPORTS
   Reg-SignalRequestMessage,
   Reg-RequestorDescription,
   Reg-SignalRequestPackage,
   Reg-SignalRequest
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   DSecond,
   MsgCount,
   RegionalExtension,
   VehicleID,
   RequestorType,
   DescriptiveName,
   Position3D,
   Angle,
   TransmissionAndSpeed,
   IntersectionReferenceID,
   RequestID,
   IntersectionAccessPoint
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





SignalRequestMessage ::= SEQUENCE {
   timeStamp       MinuteOfTheYear  OPTIONAL,
   second          DSecond,
   sequenceNumber  MsgCount         OPTIONAL,

   requests        SignalRequestList OPTIONAL,
                   -- Request Data for one or more signalized
                   -- intersections that support SRM dialogs

   requestor       RequestorDescription,
                   -- Requesting Device and other User Data
                   -- contains vehicle ID (if from a vehicle)
                   -- as well as type data and current position
                   -- and may contain additional transit data

   regional        SEQUENCE (SIZE(1..4)) OF
                   RegionalExtension {{Reg-SignalRequestMessage}} OPTIONAL,
   ...
   }


RequestorDescription ::= SEQUENCE {
   id                VehicleID,
                     -- The ID used in the BSM or CAM of the requestor
                     -- This ID is presumed not to change
                     -- during the exchange
   type              RequestorType OPTIONAL,
                     -- Information regarding all type and class data
                     -- about the requesting vehicle
   position          RequestorPositionVector OPTIONAL,
                     -- The location of the requesting vehicle
   name              DescriptiveName OPTIONAL,
                     -- A human readable name for debugging use
   -- Support for Transit requests
   routeName         DescriptiveName OPTIONAL,
                     -- A string for transit operations use
   transitStatus     TransitVehicleStatus OPTIONAL,
                     -- current vehicle state (loading, etc.)
   transitOccupancy  TransitVehicleOccupancy OPTIONAL,
                     -- current vehicle occupancy
   transitSchedule   DeltaTime OPTIONAL,
                     -- current vehicle schedule adherence

   regional          SEQUENCE (SIZE(1..4)) OF
                     RegionalExtension {{Reg-RequestorDescription}} OPTIONAL,
   ...
   }


RequestorPositionVector ::= SEQUENCE {
   position           Position3D,
   heading            Angle OPTIONAL,
   speed              TransmissionAndSpeed OPTIONAL,
   ...
   }

SignalRequestList ::= SEQUENCE (SIZE(1..32)) OF SignalRequestPackage

SignalRequestPackage ::= SEQUENCE {
   request        SignalRequest,
                  -- The specific request to the intersection
                  -- contains IntersectionID, request type,
                  -- requested action (approach/lane request)

   -- The Estimated Time of Arrival (ETA) when the service is requested
   minute         MinuteOfTheYear OPTIONAL,
   second         DSecond OPTIONAL,
   duration       DSecond OPTIONAL,
                  -- The duration value is used to provide a short interval that
                  -- extends the ETA so that the requesting vehicle can arrive at
                  -- the point of service with uncertainty or with some desired
                  -- duration of service. This concept can be used to avoid needing
                  -- to frequently update the request.
                  -- The requester must update the ETA and duration values if the
                  -- period of services extends beyond the duration time.
                  -- It should be assumed that if the vehicle does not clear the
                  -- intersection when the duration is reached, the request will
                  -- be cancelled and the intersection will revert to
                  -- normal operation.

   regional       SEQUENCE (SIZE(1..4)) OF
                  RegionalExtension {{Reg-SignalRequestPackage}} OPTIONAL,
   ...
   }

SignalRequest ::= SEQUENCE {
   -- the unique ID of the target intersection
   id            IntersectionReferenceID,

   -- The unique requestID used by the requestor
   requestID     RequestID,

   -- The type of request or cancel for priority or preempt use
   -- when a prior request is canceled, only the requestID is needed
   requestType   PriorityRequestType,

   -- In typical use either an approach or a lane number would
   -- be given, this indicates the requested
   -- path through the intersection to the degree it is known.
   inBoundLane   IntersectionAccessPoint,
                 -- desired entry approach or lane
   outBoundLane  IntersectionAccessPoint OPTIONAL,
                 -- desired exit approach or lane
                 -- the values zero is used to indicate
                 -- intent to stop within the intersection
   regional      SEQUENCE (SIZE(1..4)) OF
                 RegionalExtension {{Reg-SignalRequest}} OPTIONAL,
   ...
   }

DeltaTime ::= INTEGER (-122 .. 121)
   -- Supporting a range of +/- 20 minute in steps of 10 seconds
   -- the value of -121 shall be used when more than -20 minutes
   -- the value of +120 shall be used when more than +20 minutes
   -- the value -122 shall be used when the value is unavailable

PriorityRequestType ::= ENUMERATED {
     priorityRequestTypeReserved (0),
     priorityRequest             (1),
     priorityRequestUpdate       (2),
     priorityCancellation        (3),
     ...
     }

TransitVehicleOccupancy ::= ENUMERATED {
    occupancyUnknown    (0),
    occupancyEmpty      (1),
    occupancyVeryLow    (2),
    occupancyLow        (3),
    occupancyMed        (4),
    occupancyHigh       (5),
    occupancyNearlyFull (6),
    occupancyFull       (7)
    }

TransitVehicleStatus ::= BIT STRING {
    loading     (0), -- parking and unable to move at this time
    anADAuse    (1), -- an ADA access is in progress (wheelchairs, kneeling, etc.)
    aBikeLoad   (2), -- loading of a bicycle is in progress
    doorOpen    (3), -- a vehicle door is open for passenger access
    charging    (4), -- a vehicle is connected to charging point
    atStopLine  (5)  -- a vehicle is at the stop line for the lane it is in
    } (SIZE(8))
END

-- Use of this module defined in SAE J2735
-- Latest document release for this module is Nov 2022
-- Filename: J2735-SignalStatusMessage-2024-rel-v1.1.asn
--

SignalStatusMessage
{joint-iso-itu-t (2) country (16) us (840) organization (1) sae (114566)
v2x-communications (1) technical-committees (1) v2x-core (5) technical-reports (1)
j2735 (2735) part-0 (0) asn1-module (1) signalStatusMessage (19)
version-1 (1) version-minor-1 (1)}

DEFINITIONS AUTOMATIC TAGS ::=
BEGIN

IMPORTS
   Reg-SignalStatusMessage,
   Reg-SignalStatusPackage,
   Reg-SignalStatus
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   DSecond,
   MsgCount,
   RegionalExtension,
   VehicleID,
   RequestID,
   BasicVehicleRole,
   RequestorType,
   IntersectionAccessPoint,
   PrioritizationResponseStatus,
   IntersectionReferenceID
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





SignalStatusMessage ::= SEQUENCE {
   timeStamp       MinuteOfTheYear  OPTIONAL,
   second          DSecond,
   sequenceNumber  MsgCount         OPTIONAL,

   -- Status Data for one of more signalized intersections
   status          SignalStatusList,

   regional        SEQUENCE (SIZE(1..4)) OF
                   RegionalExtension {{Reg-SignalStatusMessage}} OPTIONAL,
   ...
   }

SignalRequesterInfo ::= SEQUENCE {
   -- These three items serve to uniquely identify the requester
   -- and the specific request to all parties
   id             VehicleID,
   request        RequestID,
   sequenceNumber MsgCount,
   role           BasicVehicleRole OPTIONAL,

   typeData       RequestorType OPTIONAL,
                  -- Used when addition data besides the role
                  -- is needed, at which point the role entry
                  -- above is not sent.
   ...
   }

SignalStatusList ::= SEQUENCE (SIZE(1..32)) OF SignalStatus

SignalStatusPackageList ::= SEQUENCE (SIZE(1..32)) OF SignalStatusPackage

SignalStatusPackage ::= SEQUENCE {
   -- The party that made the initial SRM request
   requester    SignalRequesterInfo OPTIONAL,
   -- The lanes or approaches used in the request
   inboundOn    IntersectionAccessPoint, -- estimated lane / approach of vehicle
   outboundOn   IntersectionAccessPoint OPTIONAL,

   -- The Estimated Time of Arrival (ETA) when the service is requested
   -- This data echos the data of the request
   minute       MinuteOfTheYear OPTIONAL,
   second       DSecond OPTIONAL,
      duration     DSecond OPTIONAL,

   -- the SRM status for this request
   status       PrioritizationResponseStatus,
                -- Status of request, this may include rejection

   regional     SEQUENCE (SIZE(1..4)) OF
                RegionalExtension {{Reg-SignalStatusPackage}} OPTIONAL,
   ...
   }


SignalStatus ::= SEQUENCE {
   sequenceNumber MsgCount,
                  -- changed whenever the below contents have change
   id             IntersectionReferenceID,
                  -- this provides a unique mapping to the
                  -- intersection map in question
                  -- which provides complete location
                  -- and approach/movement/lane data
                  -- as well as zones for priority/preemption
   sigStatus      SignalStatusPackageList,
                  -- a list of detailed status containing all
                  -- priority or preemption state data, both
                  -- active and pending, and who requested it
                  -- requests which are denied are also listed
                  -- here for a short period of time
   regional       SEQUENCE (SIZE(1..4)) OF
                  RegionalExtension {{Reg-SignalStatus}} OPTIONAL,
   ...
   }
END

-- Use of this module defined in SAE J2735
-- Latest document release for this module is Nov 2022
-- Filename: J2735-SPAT-2024-rel-v1.1.1.asn
--

SPAT
{joint-iso-itu-t (2) country (16) us (840) organization (1) sae (114566)
v2x-communications (1) technical-committees (1) v2x-core (5) technical-reports (1)
j2735 (2735) part-0 (0) asn1-module (1) signalPhaseAndTimingMessage (9)
version-1 (1) version-minor-1 (1)}

DEFINITIONS AUTOMATIC TAGS ::=
BEGIN

IMPORTS
   Reg-SPAT,
   Reg-AdvisorySpeed,
   Reg-ConnectionManeuverAssist,
   Reg-IntersectionState,
   Reg-MovementEvent,
   Reg-MovementState
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   MinuteOfTheYear,
   DescriptiveName,
   RegionalExtension,
   SpeedConfidence,
   RestrictionClassID,
   LaneConnectionID,
   LaneID,
   IntersectionReferenceID,
   MsgCount,
   DSecond,
   SignalGroupID,
    RoadAuthorityID
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





SPAT ::= SEQUENCE {
   timeStamp     MinuteOfTheYear OPTIONAL,
   name          DescriptiveName OPTIONAL,
                 -- human readable name for this collection
                 -- to be used only in debug mode

   intersections IntersectionStateList,
                 -- sets of SPAT data (one per intersection)

   -- If PrioritizationResponse data is required, it is found
   -- in the RegionalSPAT entry below

   regional      SEQUENCE (SIZE(1..4)) OF
                 RegionalExtension {{Reg-SPAT}} OPTIONAL,
   ...
   }


AdvisorySpeed ::= SEQUENCE {
   type        AdvisorySpeedType,
               -- the type of advisory which this is.
   speed       SpeedAdvice OPTIONAL,
               -- See Section 11 for converting and translating speed
               -- expressed in mph into units of m/s
               -- This element is optional ONLY when superceded
               -- by the presence of a regional speed element found in
               -- Reg-AdvisorySpeed entry
   confidence  SpeedConfidence OPTIONAL,
               -- A confidence value for the above speed
   distance    ZoneLength OPTIONAL,
               -- Unit = 1 meter,
               -- The distance indicates the region for which the advised speed
               -- is recommended, it is specified upstream from the stop bar
               -- along the connected egressing lane
   class       RestrictionClassID OPTIONAL,
               -- the vehicle types to which it applies
               -- when absent, the AdvisorySpeed applies to
               -- all motor vehicle types
   regional    SEQUENCE (SIZE(1..4)) OF
               RegionalExtension {{Reg-AdvisorySpeed}} OPTIONAL,
   ...
   }


AdvisorySpeedList ::= SEQUENCE (SIZE(1..16)) OF AdvisorySpeed


ConnectionManeuverAssist ::= SEQUENCE {
   connectionID         LaneConnectionID,
                        -- the common connectionID used by all lanes to which
                        -- this data applies
                        -- (this value traces to ConnectsTo entries in lanes)
   -- Expected Clearance Information
   queueLength          ZoneLength OPTIONAL,
                        -- Unit = 1 meter, 0 = no queue
                        -- The distance from the stop line to the back
                        -- edge of the last vehicle in the queue,
                        -- as measured along the lane center line.
   availableStorageLength ZoneLength OPTIONAL,
                        -- Unit = 1 meter, 0 = no space remains
                        -- Distance (e.g., beginning from the downstream
                        -- stop-line up to a given distance) with a high
                        -- probability for successfully executing the
                        -- connecting maneuver between the two lanes
                        -- during the current cycle.
                        -- Used for enhancing the awareness of vehicles
                        -- to anticipate if they can pass the stop line
                        -- of the lane. Used for optimizing the green wave,
                        -- due to knowledge of vehicles waiting in front
                        -- of a red light (downstream).
                        -- The element nextTime in TimeChangeDetails
                        -- in the containing data frame contains the next
                        -- timemark at which an active phase is expected,
                        -- a form of storage flush interval.
   waitOnStop           WaitOnStopline OPTIONAL,
                        -- If "true," the vehicles on this specific connecting
                        -- maneuver have to stop on the stop-line and not
                        -- to enter the collision area
   pedBicycleDetect     PedestrianBicycleDetect OPTIONAL,
                        -- true if ANY ped or bicycles are detected crossing
                        -- the above lanes. Set to false ONLY if there is a
                        -- high certainty that there are none present,
                        -- otherwise element is not sent.
   regional  SEQUENCE (SIZE(1..4)) OF
             RegionalExtension {{Reg-ConnectionManeuverAssist}} OPTIONAL,
   ...
   }


EnabledLaneList ::= SEQUENCE (SIZE(1..16)) OF LaneID
   -- The unique ID numbers for each
   -- lane object which is 'active'
   -- as part of the dynamic map contents.


IntersectionState ::= SEQUENCE {
   name         DescriptiveName OPTIONAL,
                -- human readable name for intersection
                -- to be used only in debug mode
   id           IntersectionReferenceID,
                -- A globally unique value set, consisting of a
                -- regionID and intersection ID assignment
                -- provides a unique mapping to the
                -- intersection MAP in question
                -- which provides complete location
                -- and approach/move/lane data
   revision     MsgCount,
   status       IntersectionStatusObject,
                -- general status of the controller(s)
   moy          MinuteOfTheYear OPTIONAL,
                -- Minute of current UTC year
                -- used only with messages to be archived
   timeStamp    DSecond OPTIONAL,
                -- the mSec point in the current UTC minute that
                -- this message was constructed
   enabledLanes EnabledLaneList OPTIONAL,
                -- a list of lanes where the RevocableLane bit
                -- has been set which are now active and
                -- therefore part of the current intersection
   states       MovementList,
                -- Each Movement is given in turn
                -- and contains its signal phase state,
                -- mapping to the lanes it applies to, and
                -- point in time it will end, and it
                -- may contain both active and future states
   maneuverAssistList  ManeuverAssistList OPTIONAL,
                -- Assist data

   regional     SEQUENCE (SIZE(1..4)) OF
                RegionalExtension {{Reg-IntersectionState}} OPTIONAL,
   ...,
   roadAuthorityID      RoadAuthorityID      OPTIONAL
   -- Mandatory if roadRegulatorID is set to 0
   }


IntersectionStateList ::= SEQUENCE (SIZE(1..32)) OF  IntersectionState


ManeuverAssistList ::= SEQUENCE (SIZE(1..16)) OF ConnectionManeuverAssist


MovementEventList ::= SEQUENCE (SIZE(1..16)) OF MovementEvent


MovementEvent ::= SEQUENCE {
   eventState   MovementPhaseState,
                -- Consisting of:
                -- Phase state (the basic 11 states)
                -- Directional, protected, or permissive state

   timing       TimeChangeDetails OPTIONAL,
                -- Timing Data in UTC time stamps for event
                -- includes start and min/max end times of phase
                -- confidence and estimated next occurrence

   speeds       AdvisorySpeedList OPTIONAL,
                -- various speed advisories for use by
                -- general and specific types of vehicles
                -- supporting green-wave and other flow needs
                -- See Section 11 for converting and translating
                -- speed expressed in mph into units of m/s

   regional     SEQUENCE (SIZE(1..4)) OF
                RegionalExtension {{Reg-MovementEvent}} OPTIONAL,
   ...
   }


MovementList ::= SEQUENCE (SIZE(1..255)) OF MovementState


MovementState ::= SEQUENCE {
   movementName       DescriptiveName OPTIONAL,
                      -- uniquely defines movement by name
                      -- human readable name for intersection
                      -- to be used only in debug mode
   signalGroup        SignalGroupID,
                      -- the group id is used to map to lists
                      -- of lanes (and their descriptions)
                      -- which this MovementState data applies to
                      -- see comments in the Remarks for usage details
   state-time-speed   MovementEventList,
                      -- Consisting of sets of movement data with:
                      -- a)  SignalPhaseState
                      -- b)  TimeChangeDetails,  and
                      -- c)  AdvisorySpeeds      (optional )
                      -- Note one or more of the movement events may be for
                      -- a future time and that this allows conveying multiple
                      -- predictive phase and movement timing for various uses
                      -- for the current signal group
   maneuverAssistList ManeuverAssistList OPTIONAL,
                      -- This information may also be placed in the
                      -- IntersectionState when common information applies to
                      -- different lanes in the same way
   regional           SEQUENCE (SIZE(1..4)) OF
                      RegionalExtension {{Reg-MovementState}} OPTIONAL,
   ...
   }


TimeChangeDetails ::= SEQUENCE {
   startTime   TimeMark           OPTIONAL,
               -- When this future phase will start
   minEndTime  TimeMark,
               -- Expected shortest end time
   maxEndTime  TimeMark           OPTIONAL,
               -- Expected longest end time

   likelyTime  TimeMark           OPTIONAL,
               -- Best predicted value based on other data
   confidence  TimeIntervalConfidence OPTIONAL,
               -- Applies to above time element only

   nextTime    TimeMark           OPTIONAL
               -- A rough estimate of time when
               -- this phase may next occur again
               -- used to support various ECO driving power
               -- management needs.
   }

AdvisorySpeedType ::= ENUMERATED {
    none       (0),
    greenwave  (1),
    ecoDrive   (2),
    transit    (3),
    ...
    } -- Note: subject to further growth

IntersectionStatusObject ::= BIT STRING {
    manualControlIsEnabled                (0),
      -- Timing reported is per programmed values, etc. but person
      -- at cabinet can manually request that certain intervals are
      -- terminated early (e.g., green).
    stopTimeIsActivated                   (1),
      -- And all counting/timing has stopped.
    failureFlash                          (2),
      -- Above to be used for any detected hardware failures,
      -- e.g., conflict monitor as well as for police flash
    preemptIsActive                       (3),
    signalPriorityIsActive                (4),

   -- Additional states
    fixedTimeOperation                    (5),
      -- Schedule of signals is based on time only
      -- (i.e., the state can be calculated)
    trafficDependentOperation             (6),
      -- Operation is based on different levels of traffic parameters
      -- (requests, duration of gaps or more complex parameters)
    standbyOperation                      (7),
      -- Controller: partially switched off or partially amber flashing
    failureMode                           (8),
      -- Controller has a problem or failure in operation
    off                                   (9),
      -- Controller is switched off

   -- Related to MAP and SPAT bindings
    recentMAPmessageUpdate                (10),
      -- Map revision with content changes
    recentChangeInMAPassignedLanesIDsUsed (11),
      -- Change in MAP's assigned lanes used (lane changes)
      -- Changes in the active lane list description
    noValidMAPisAvailableAtThisTime       (12),
      -- MAP (and various lanes indexes) not available
    noValidSPATisAvailableAtThisTime      (13)
      -- SPAT system is not working at this time

    -- Bits 14,15 reserved at this time and shall be zero
    } (SIZE(16))

MovementPhaseState ::= ENUMERATED {
    -- Note that based on the regions and the operating mode not every
    -- phase will be used in all transportation modes and that not
    -- every phase will be used in all transportation modes

    unavailable (0),
      -- This state is used for unknown or error
    dark (1),
      -- The signal head is dark (unlit)

   -- Reds
    stop-Then-Proceed (2),
      -- Often called 'flashing red' in US
      -- Driver Action:
      --   Stop vehicle at stop line.
      --   Do not proceed unless it is safe.
      -- Note that the right to proceed either right or left when
      -- it is safe may be contained in the lane description to
      -- handle what is called a 'right on red'
    stop-And-Remain (3),
      -- e.g., called 'red light' in US
      -- Driver Action:
      --   Stop vehicle at stop line.
      --   Do not proceed.
      -- Note that the right to proceed either right or left when
      -- it is safe may be contained in the lane description to
      -- handle what is called a 'right on red'

   -- Greens
    pre-Movement (4),
      -- Not used in the US, red+yellow partly in EU
      -- Driver Action:
      --   Stop vehicle.
      --   Prepare to proceed (pending green)
      --   (Prepare for transition to green/go)
    permissive-Movement-Allowed (5),
      -- Often called 'permissive green' in US
      -- Driver Action:
      --   Proceed with caution,
      --   must yield to all conflicting traffic
      -- Conflicting traffic may be present
      -- in the intersection conflict area
    protected-Movement-Allowed (6),
      -- Often called 'protected green' in US
      -- Driver Action:
      --   Proceed, in indicated (allowed) direction.
      --   This movement has the right-of-way.

   -- Yellows / Ambers
   -- The vehicle is not allowed to cross the stop bar if it is possible
   -- to stop without danger.
    permissive-clearance (7),
      -- Often called 'permissive yellow' in US
      -- Driver Action:
      --   Prepare to stop.
      --   Proceed if unable to stop,
      --   Clear Intersection.
      -- Conflicting traffic may be present
      -- in the intersection conflict area
    protected-clearance (8),
      -- Often called 'protected yellow' in US
      -- Driver Action:
      --   Prepare to stop.
      --   Proceed if unable to stop,
      --   in indicated direction (to connected lane)
      --   Clear Intersection.

    caution-Conflicting-Traffic (9)
      -- Often called 'flashing yellow' in US
      -- Often used for extended periods of time
      -- Driver Action:
      --   Proceed with caution,
      -- Conflicting traffic may be present
      -- in the intersection conflict area
    }
    -- The above number assignments are not used with UPER encoding
    -- and are only to be used with DER or implicit encoding

PedestrianBicycleDetect ::= BOOLEAN
                 -- true if ANY Pedestrians or Bicyclists are
                 -- detected crossing the target lane or lanes

SpeedAdvice ::= INTEGER (0..500)
    -- LSB units are 0.1 m/s^2
    -- the value 499 shall be used for values at or greater than 49.9 m/s
    -- the value 500 shall be used to indicate that speed is unavailable

TimeIntervalConfidence ::= INTEGER (0..15)
   -- Value   Probability
   --   0         21%
   --   1         36%
   --   2         47%
   --   3         56%
   --   4         62%
   --   5         68%
   --   6         73%
   --   7         77%
   --   8         81%
   --   9         85%
   --   10        88%
   --   11        91%
   --   12        94%
   --   13        96%
   --   14        98%
   --   15        100%

TimeMark ::= INTEGER (0..36111)
   -- In units of 1/10th second from UTC time
   -- A range of 0~35999 covers one hour
   -- The values 36000..36009 are used when a leap second occurs
   -- The values 36010..36110 are reserved for future use
   -- 36111 is to be used when the value is undefined or unknown
   -- Note that this is NOT expressed in GPS time
   -- or in local time

WaitOnStopline ::= BOOLEAN --
         -- True or False
         -- If "true," the vehicles on this specific connecting
         -- maneuver have to stop on the stop-line
         -- and not to enter the collision area

ZoneLength ::= INTEGER (0..10000)
    -- Unit = 1 meter, 0 = unknown,
    -- The value 10000 to be used for Distances >=10000 m
    -- (e.g., from known point to another point along a
    -- known path, often against traffic flow direction
    -- when used for measuring queues)
END

-- Use of this module defined in SAE J2735
-- Latest document release for this module is TBD (not yet released)
-- Filename: J2735-TrafficLightStatusMessage-2024-rel-v1.1.1.asn
--

TrafficLightStatusMessage
{joint-iso-itu-t (2) country (16) us (840) organization (1) sae (114566)
v2x-communications (1) technical-committees (1) v2x-core (5) technical-reports (1)
j2735 (2735) part-0 (0) asn1-module (1) trafficLightStatusMessage (50)
version-1 (1) version-minor-1 (1)}

DEFINITIONS AUTOMATIC TAGS ::=
BEGIN

IMPORTS
    DDateTime,
    Latitude,
    Longitude
        FROM Common {joint-iso-itu-t (2) country (16) us (840) organization (1) sae (114566)
      v2x-communications (1) technical-committees (1) v2x-core (5) technical-reports (1)
      j2735 (2735) part-0 (0) asn1-module (1) common (38)
      version-1 (1)  version-minor-1 (1)};

TrafficLightStatusMessage ::= SEQUENCE {
    trafficLightID       TrafficLightID,
    -- identifier of the traffic light controller that provides the status
    -- information
    long                Longitude   OPTIONAL,
    -- longitude of the center of the intersection where the traffic light
    -- controller is located
    lat                 Latitude    OPTIONAL,
    -- latitude of the center of the intersection where the traffic light
    -- controller is located
    operationStatus     TrafficLightOperationStatus,
    -- status of operations of traffic light controller
    controllerStatus    TrafficLightControllerStatus,
    -- status of traffic light controller
    cyclecounter        TimeInSecond-B16,
    -- time elapsed since current signal phase started
    cycletime           TimeInSecond-B16,
    -- duration of signal phase
    currentTime         DDateTime,
    -- time detected
    trafficLightStatus  TrafficLightStatusList,
    -- signal state information
    ...
}

TrafficLightStatusList ::= SEQUENCE (SIZE(1..255)) OF TrafficLightStatus

TrafficLightStatus ::= SEQUENCE {
    trafficLightType            TrafficLightType,
    -- type of traffic light
    -- pedestrian traffic lights, bicycle traffic lights, etc
    consecutiveTrafficLight     ConsecutiveTrafficLight,
    -- interconnection information
    -- When connecting two or more intersection traffic lights to one
    -- traffic signal controller, it includes signal information of
    -- intersections other than main intersection
    trafficLightIntervalType    TrafficLightIntervalType,
    -- Type of traffic signal cycle (fixed, variable cycle)
    pedestrianCall              PedestrianCall,
    -- Whether pedestrian button is pressed or not
    actuatedinterval            ActuatedInterval,
    -- extended or actuated signal control cycle
    permissiveNonProtected      PermissiveNonProtected,
    -- permission/non-protection
    lightingStatus              TrafficLightingStatus,
    -- traffic light illuminated state
    maxIntervalLength           TimeInSecond-B8,
    -- max duration of signal light activation status
    remainingTime               TimeInSecond-B8,
    -- remaining time of the current signal state
    directionCode               TrafficLightDirectionCode,
    -- Direction of entry for vehicles that should obey this signal
    reserved                    ReservedBit,
    -- reserved field
    ...
}

ActuatedInterval ::= BOOLEAN

ConsecutiveTrafficLight ::= ENUMERATED {
    none    (0),
    first   (1),
    second  (2),
    ...
}

PedestrianCall ::= BOOLEAN

PermissiveNonProtected ::= ENUMERATED {
    none        (0),  -- Non-protected movement is not allowed.
    permissive  (1),  -- Non-protected movement is allowed.
    ...
}

ReservedBit ::= BOOLEAN

TimeInSecond-B16 ::= INTEGER (0..65535)

TimeInSecond-B8 ::= INTEGER (0..255)
-- 255 means invalid value

TrafficLightControllerStatus ::= BIT STRING {
    conflict            (0),
    -- Contradiction state is the state where signal operation is stopped due to
    -- conflicting signals, indicating all-red flashing at the entire intersection
    -- If there is a contradiction or inconsistency, it is set to 1, and if it is
    -- normal, it is set to 0
    center-comm-error   (1),
    -- If a communication failure with the center occurs, the value is set to 1,
    -- indicating an abnormal communication status
    -- If communication is normal, the value will be set to 0, indicating that the
    -- controller is operating independently
    scu-comm-error      (2),
    -- If there is a communication problem with the Signal Control Unit(SCU),
    -- the value is set to 1
    -- the value 1 indicates that there is a communication problem and the status of
    -- the signal output cannot be determined
    -- If there is no communication problem with the SCU, the value is set to 0
    -- It means that the communication is normal
    reserved1           (3),
    -- the reserved field that is pre-allocated for future use in a data structure
    reserved2           (4),
    reserved3           (5),
    reserved4           (6),
    reserved5           (7)
} (SIZE(8, ...))

TrafficLightDirectionCode ::= INTEGER (0..359) -- 0 degrees is due North

TrafficLightID ::= CHOICE {
    id  INTEGER,            --
    oid OBJECT IDENTIFIER   -- for extensibility purposes
}

TrafficLightIntervalType ::= ENUMERATED {
    static      (0),  -- interval is static
    variable    (1),  -- interval is variable
    ...
}

TrafficLightOperationStatus ::= BIT STRING {
    manual          (0),
    -- If it is normal, it is set to 0, and otherwise, it is set to 1
    flashing        (1),
    -- If it is flashing, it is set to 1, and if it is normal, it is set to 0
    off             (2),
    -- a state of being turned off
    -- If it is turned off, it is set to 1, and if it is normal,
    -- it is set to 0
    actuated        (3),
    -- If actuated system is in progress, it is set to 1,
    -- and if it is normal, it is set to 0
    transition      (4),
    -- If it is transition, it is set to 1, and if it is normal,
    -- it is set to 0
    priority        (5),
    -- If it is transition, it is set to 1,
    -- and if it is normal, it is set to 0
    holding-phase   (6),
    -- It is set to 1 when the priority signal is in service, and 0
    -- when it is not
    reserved        (7)
    -- the reserved field for future us
} (SIZE(8, ...))

TrafficLightingStatus ::= ENUMERATED {
    off             (0),
    red-on          (1),
    yellow-on       (2),
    green-on        (3),
    red-blinking    (4),
    yellow-blinking (5),
    green-blinking  (6),
    ...
}

TrafficLightType ::= ENUMERATED {
    reserved        (0),
    straight        (1),
    left-turn       (2),
    pedestrian      (3),
    bicycle         (4),
    right-turn      (5),
    bus             (6),
    u-turn          (7),
    ...
}

END-- Use of this module defined in SAE J2735
-- Latest document release for this module is Nov 2022
-- Filename: J2735-TravelerInformation-2024-rel-v1.1.1.asn
--

TravelerInformation
{joint-iso-itu-t (2) country (16) us (840) organization (1) sae (114566)
v2x-communications (1) technical-committees (1) v2x-core (5) technical-reports (1)
j2735 (2735) part-0 (0) asn1-module (1) travelerInformation (20)
version-1 (1) version-minor-1 (1)}

DEFINITIONS AUTOMATIC TAGS ::=
BEGIN

IMPORTS
   Reg-TravelerInformation,
   Reg-GeographicalPath,
   Reg-GeometricProjection,
   Reg-NodeAttributeSetLL,
   Reg-NodeOffsetPointLL
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   ITIScodes,
   ITIScodesAndText
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)}
   MsgCount,
   MinuteOfTheYear,
   RegionalExtension,
   Position3D,
   DescriptiveName,
   RoadSegmentReferenceID,
   LaneWidth,
   HeadingSlice,
   Extent,
   OffsetLL-B18,
   LaneDataAttributeList,
   Offset-B10,
   Node-LLmD-64b,
   NodeListXY,
   SSPindex,
   FurtherInfoID,
   DYear,
    FrictionInformation
      FROM Common {joint-iso-itu-t (2) country (16) us (840) organization (1) sae (114566)
      v2x-communications (1) technical-committees (1) v2x-core (5) technical-reports (1)
      j2735 (2735) part-0 (0) asn1-module (1) common (38)
      version-1 (1) version-minor-1 (1)};





TravelerInformation ::= SEQUENCE {
   msgCnt      MsgCount,
   timeStamp   MinuteOfTheYear OPTIONAL,
   packetID    UniqueMSGID     OPTIONAL,
   urlB        URL-Base        OPTIONAL,

   -- A set of one or more self contained
   -- traveler information messages (frames)
   dataFrames  TravelerDataFrameList,

   regional    SEQUENCE (SIZE(1..4)) OF
               RegionalExtension {{Reg-TravelerInformation}} OPTIONAL,
   ...
   }


Circle ::= SEQUENCE {
   center   Position3D,
   radius   Radius-B12,
   units    DistanceUnits
   }


GeographicalPath ::= SEQUENCE {
   name             DescriptiveName          OPTIONAL,
   id               RoadSegmentReferenceID   OPTIONAL,
   anchor           Position3D               OPTIONAL,
   laneWidth        LaneWidth                OPTIONAL,
   directionality   DirectionOfUse           OPTIONAL,
   closedPath       BOOLEAN                  OPTIONAL,
                    -- when true, last point closes to first
   direction        HeadingSlice             OPTIONAL,
                    -- field of view over which this applies
   description CHOICE  {
      path         OffsetSystem,
                   -- The XYZ and LLH system of paths
      geometry     GeometricProjection,
                   -- A projected circle from a point
      oldRegion    ValidRegion,
                   -- Legacy method, no longer recommended for use
      ...
      } OPTIONAL,

   regional   SEQUENCE (SIZE(1..4)) OF
            RegionalExtension {{Reg-GeographicalPath}} OPTIONAL,
   ...
   }


GeometricProjection ::= SEQUENCE {
   direction        HeadingSlice,
                    -- field of view over which this applies,
   extent           Extent OPTIONAL,
                    -- the spatial distance over which this
                    -- message applies and should be presented
   laneWidth        LaneWidth OPTIONAL, -- used when a width is needed
   circle           Circle, -- A point and radius

   regional         SEQUENCE (SIZE(1..4)) OF
                    RegionalExtension {{Reg-GeometricProjection}} OPTIONAL,
   ...
   }


ExitService ::= SEQUENCE (SIZE(1..16)) OF SEQUENCE {
  item CHOICE    {
       itis   ITIScodes,
       text   ITIStextPhrase
       }
  }


GenericSignage ::= SEQUENCE (SIZE(1..16)) OF SEQUENCE {
  item CHOICE    {
       itis   ITIScodes,
       text   ITIStextPhrase
       }
  }


SpeedLimit ::= SEQUENCE (SIZE(1..16)) OF SEQUENCE {
  item CHOICE    {
       itis   ITIScodes,
       text   ITIStextPhrase
       }
  }


WorkZone ::= SEQUENCE (SIZE(1..16)) OF SEQUENCE {
  item CHOICE    {
       itis   ITIScodes,
       text   ITIStextPhrase
       }
  }


Node-LL-24B ::= SEQUENCE {
   -- ranges of +- 0.0002047 degrees
   -- ranges of +- 22.634554 meters at the equator
   lon  OffsetLL-B12,
   lat  OffsetLL-B12
   }


Node-LL-28B ::= SEQUENCE {
   -- ranges of +- 0.0008191 degrees
   -- ranges of +- 90.571389 meters at the equator
   lon  OffsetLL-B14,
   lat  OffsetLL-B14
   }


Node-LL-32B ::= SEQUENCE {
   -- ranges of +- 0.0032767 degrees
   -- ranges of +- 362.31873 meters at the equator
   lon  OffsetLL-B16,
   lat  OffsetLL-B16
   }


Node-LL-36B ::= SEQUENCE {
   -- ranges of +- 0.0131071 degrees
   -- ranges of +- 01.449308 Kmeters at the equator
   lon  OffsetLL-B18,
   lat  OffsetLL-B18
   }


Node-LL-44B ::= SEQUENCE {
   -- ranges of +- 0.2097151 degrees
   -- ranges of +- 23.189096 Kmeters at the equator
   lon  OffsetLL-B22,
   lat  OffsetLL-B22
   }


Node-LL-48B ::= SEQUENCE {
   -- ranges of +- 0.8388607 degrees
   -- ranges of +- 92.756481 Kmeters at the equator
   lon  OffsetLL-B24,
   lat  OffsetLL-B24
   }


NodeAttributeLLList ::= SEQUENCE (SIZE(1..8)) OF NodeAttributeLL


NodeAttributeSetLL ::= SEQUENCE {
   localNode    NodeAttributeLLList OPTIONAL,
                -- Attribute states which pertain to this node point
   disabled     SegmentAttributeLLList OPTIONAL,
                -- Attribute states which are disabled at this node point
   enabled      SegmentAttributeLLList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation
                -- at this node from this node onwards, in 1 cm steps
                -- elevations between nodes are a linear taper between pts
                -- the value of zero shall not be sent here
   regional     SEQUENCE (SIZE(1..4)) OF
                RegionalExtension {{Reg-NodeAttributeSetLL}} OPTIONAL,
   ...
   }


NodeListLL ::= CHOICE {
   nodes     NodeSetLL,
             -- a path made up of two or more
             -- LL node points and any attributes
             -- defined in those nodes
   -- Additional choices will be added in time
   ...
   }


NodeLL ::= SEQUENCE {
   delta       NodeOffsetPointLL,
               -- A choice of which Lat,Lon offset value to use
               -- this includes various delta values as well a regional choices
   attributes  NodeAttributeSetLL OPTIONAL,
               -- Any optional Attributes which are needed
               -- This includes changes to the current lane width and elevation
   ...
   }


NodeOffsetPointLL ::= CHOICE {
   -- Nodes with LL content         Span at the equator when using a zoom of one:
   node-LL1         Node-LL-24B,    -- within +- 22.634554  meters of last node
   node-LL2         Node-LL-28B,    -- within +- 90.571389  meters of last node
   node-LL3         Node-LL-32B,    -- within +- 362.31873  meters of last node
   node-LL4         Node-LL-36B,    -- within +- 01.449308 Kmeters of last node
   node-LL5         Node-LL-44B,    -- within +- 23.189096 Kmeters of last node
   node-LL6         Node-LL-48B,    -- within +- 92.756481 Kmeters of last node
   node-LatLon      Node-LLmD-64b,  -- node is a full 32b Lat/Lon range
   regional         RegionalExtension {{Reg-NodeOffsetPointLL}}
                                    -- node which follows is of a
                                    -- regional definition type
   }


NodeSetLL ::= SEQUENCE (SIZE(2..63)) OF NodeLL


OffsetSystem ::= SEQUENCE {
   scale      Zoom OPTIONAL,
   offset     CHOICE {
      xy        NodeListXY, -- offsets of 1.0 centimeters
      ll        NodeListLL  -- offsets of 0.1 microdegrees
      }
   }


RegionList ::= SEQUENCE (SIZE(1..64)) OF RegionOffsets
   -- the Position3D ref point (starting point or anchor)
   -- is found in the outer object.


RegionOffsets ::= SEQUENCE {
   xOffset  OffsetLL-B16,
   yOffset  OffsetLL-B16,
   zOffset  OffsetLL-B16 OPTIONAL
            -- all in signed values where
            -- the LSB is in units of 1 meter
   }


RegionPointSet ::= SEQUENCE {
   anchor           Position3D  OPTIONAL,
   scale            Zoom OPTIONAL,
   nodeList         RegionList,
                    -- path details of the regions outline
   ...
   }


RoadSignID ::= SEQUENCE {
   position        Position3D,
                   -- Location of sign
   viewAngle       HeadingSlice,
                   -- Vehicle direction of travel while
                   -- facing active side of sign
   mutcdCode       MUTCDCode OPTIONAL,
                   -- Tag for MUTCD code or "generic sign"
   crc             MsgCRC OPTIONAL
                   -- Used to provide a check sum
   }


SegmentAttributeLLList ::= SEQUENCE (SIZE(1..8)) OF SegmentAttributeLL


ShapePointSet ::= SEQUENCE {
   anchor           Position3D     OPTIONAL,
   laneWidth        LaneWidth      OPTIONAL,
   directionality   DirectionOfUse OPTIONAL,
   nodeList         NodeListXY,    -- XY path details of the lane and width
   ...
   }


TravelerDataFrameList ::= SEQUENCE (SIZE(1..8)) OF TravelerDataFrame


TravelerDataFrame ::= SEQUENCE {
   -- Part I, Frame header
   doNotUse1    SSPindex,
        -- always set to 0 and carries no meaning;
        -- legacy field maintained for backward compatibility
   frameType   TravelerInfoType,  -- (enum, advisory or road sign)
   msgId CHOICE {
         furtherInfoID   FurtherInfoID, -- links to ATIS msg
         roadSignID      RoadSignID     -- an ID to other data
         },
   startYear   DYear OPTIONAL,  -- only if needed
   startTime   MinuteOfTheYear,
   durationTime MinutesDuration,
   priority    SignPriority,

   -- Part II, Applicable Regions of Use
   doNotUse2  SSPindex, -- set to 0
   regions SEQUENCE (SIZE(1..16)) OF GeographicalPath,

   -- Part III, Content
   doNotUse3    SSPindex,  -- set to 0
   doNotUse4    SSPindex,  -- set to 0
   content  CHOICE {
            advisory     ITIScodesAndText,
                         -- typical ITIS warnings
            workZone     WorkZone,
                         -- work zone signs and directions
            genericSign  GenericSignage,
                         -- MUTCD signs and directions
            speedLimit   SpeedLimit,
                         -- speed limits and cautions
            exitService  ExitService
                         -- roadside avaiable services
            -- other types may be added in future revisions
            },
   url     URL-Short OPTIONAL,  -- May link to image or other content
   ...,
   -- New Part III content
   contentNew    TravelerDataFrameNewPartIIIContent
   }

TravelerDataFrameNewPartIIIContent ::= CHOICE {
   -- Add new content types for future revisions here
   frictionInfo    FrictionInformation,
   ...
   }

ValidRegion ::= SEQUENCE {
   direction         HeadingSlice,
                     -- field of view over which this applies,
   extent            Extent OPTIONAL,
                     -- the spatial distance over which this
                     -- message applies and should be presented
                     -- to the driver
   area    CHOICE  {
      shapePointSet  ShapePointSet,
                     -- A short road segment
      circle         Circle,
                     -- A point and radius
      regionPointSet RegionPointSet
                     -- Wide area enclosed regions
      }
   }

DirectionOfUse ::= ENUMERATED {
   unavailable (0), -- unknown or NA, not typically used in valid expressions
   forward     (1), -- direction of travel follows node ordering
   reverse     (2), -- direction of travel is the reverse of node ordering
   both        (3)  -- direction of travel allowed in both directions
   }

DistanceUnits ::= ENUMERATED {
   centimeter  (0),
   cm2-5       (1), -- Steps of 2.5 centimeters
   decimeter   (2),
   meter       (3),
   kilometer   (4),
   foot        (5), -- US foot, 0.3048 meters exactly
   yard        (6), -- three US feet
   mile        (7)  -- US mile (5280 US feet)
   }

ITIStextPhrase ::= IA5String (SIZE(1..16))

MinutesDuration ::= INTEGER (0..32000) -- units of minutes

MsgCRC ::= OCTET STRING (SIZE(2)) -- created with the CRC-CCITT polynomial

MUTCDCode ::= ENUMERATED {
   none            (0), -- non-MUTCD information
   regulatory      (1), -- "R" Regulatory signs
   warning         (2), -- "W" warning signs
   maintenance     (3), -- "M" Maintenance and construction
   motoristService (4), -- Motorist Services
   guide           (5), -- "G" Guide signs
   rec             (6), -- Recreation and Cultural Interest
   ...
   }

NodeAttributeLL ::= ENUMERATED {
   -- Various values which pertain only to the current node point

   -- General Items
   reserved,
   stopLine,             -- point where a mid-path stop line exists
                         -- See also 'do not block' for segments

   -- Path finish details
   roundedCapStyleA,      -- Used to control final path rounded end shape
                          -- with edge of curve at final point in a circle
   roundedCapStyleB,      -- Used to control final path rounded end shape
                          -- with edge of curve extending 50% of width past
                          -- final point in a circle

   -- Topography Points (items with no concept of a distance along the path)
   mergePoint,           -- Japan merge with 1 or more lanes
   divergePoint,         -- Japan diverge with 1 or more lanes
   downstreamStopLine,   -- Japan style downstream intersection
                                   -- (a 2nd intersection) stop line
   downstreamStartNode,  -- Japan style downstream intersection
                                   -- (a 2nd intersection) start node

   -- Pedestrian Support Attributes
   closedToTraffic,      -- where a pedestrian may NOT go
                         -- to be used during construction events
   safeIsland,           -- a pedestrian safe stopping point
                         -- also called a traffic island
                         -- This usage described a point feature on a path,
                         -- other entries can describe a path
   curbPresentAtStepOff, -- the sidewalk to street curb is NOT
                         -- angled where it meets the edge of the
                         -- roadway (user must step up/down)

   -- Lane geometry details  (see standard for defined shapes)
   hydrantPresent,       -- Or other services access
   ...
   }

OffsetLL-B12 ::= INTEGER (-2048..2047)
   -- A range of +- 0.0002047 degrees
   -- In LSB units of 0.1 microdegrees (unless a zoom is employed)

OffsetLL-B14 ::= INTEGER (-8192..8191)
   -- A range of +- 0.0008191 degrees
   -- In LSB units of 0.1 microdegrees (unless a zoom is employed)

OffsetLL-B16 ::= INTEGER (-32768..32767)
   -- A range of +- 0.0032767 degrees
   -- In LSB units of 0.1 microdegrees (unless a zoom is employed)

OffsetLL-B22 ::= INTEGER (-2097152..2097151)
   -- A range of +- 0.2097151 degrees
   -- In LSB units of 0.1 microdegrees (unless a zoom is employed)

OffsetLL-B24 ::= INTEGER (-8388608..8388607)
   -- A range of +- 0.8388607 degrees
   -- In LSB units of 0.1 microdegrees (unless a zoom is employed)

Radius-B12 ::= INTEGER (0..4095)
   -- with the LSB unit value determined elsewhere
   -- the value 4095 shall be used for unknown

SegmentAttributeLL ::= ENUMERATED {
   -- Various values which can be Enabled and Disabled for a lane segment

   -- General Items
   reserved                  ,
   doNotBlock                ,  -- segment where a vehicle
                                -- may not come to a stop
   whiteLine                 ,  -- segment where lane crossing not allowed
                                -- such as the final few meters of a lane

   -- Porous Lane states, merging, turn outs, parking etc.

   mergingLaneLeft           ,  -- indicates porous lanes
   mergingLaneRight          ,

   curbOnLeft                ,  -- indicates presence of curbs
   curbOnRight               ,

   loadingzoneOnLeft         ,  -- loading or drop off zones
   loadingzoneOnRight        ,

   turnOutPointOnLeft        ,  -- opening to adjacent street/alley/road
   turnOutPointOnRight       ,

   adjacentParkingOnLeft     , -- side of road parking
   adjacentParkingOnRight    ,

   -- Bike Lane Needs
   adjacentBikeLaneOnLeft    , -- presence of marked bike lanes
   adjacentBikeLaneOnRight   ,
   sharedBikeLane            , -- right of way is shared with bikes
                               -- who may occupy entire lane width
   bikeBoxInFront            ,

   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley
                               -- not used for crossing tracks


   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb
                               -- but at least 1 meter remains open for use
                               -- and at-grade passage

   -- Lane geometry details  (see standard for defined shapes)
   taperToLeft               , -- Used to control final path shape
   taperToRight              , -- Used to control final path shape
   taperToCenterLine         , -- Used to control final path shape

   -- Parking Lane and Curb Attributes
   parallelParking           , --
   headInParking             , -- Parking at an angle with the street
   freeParking               , -- no restriction on use of parking
   timeRestrictionsOnParking , -- Parking is not permitted at all times
                               -- typically used when the 'parking' lane
                               -- becomes a driving lane at times
   costToPark                , -- Used where parking has a cost
   midBlockCurbPresent       , -- a protruding curb near lane edge
   unEvenPavementPresent     , -- a disjoint height at lane edge
   ...
   }

SignPriority ::= INTEGER (0..7)
   -- 0 as least, 7 as most

TravelerInfoType ::= ENUMERATED {
     unknown            (0),
     advisory           (1),
     roadSignage        (2),
     commercialSignage  (3),
     ...
     }

UniqueMSGID ::= OCTET STRING (SIZE(9))

URL-Base ::= IA5String (SIZE(1..45))

URL-Short ::= IA5String (SIZE(1..15))

Zoom ::= INTEGER (0..15)
   -- A zoom scale applied in units of 2^N
   -- A value of 0 is a 1:1 zoom (no zoom)
   -- A value of 1 is a 2:1 zoom
   -- A value of 2 is a 4:1 zoom, etc.
   -- The zoom value is applied to one or more offsets
   -- increase the span or range while reducing its precision
   -- The absence of a zoom, any offset element in a data
   -- frame implies a 1:1 zoom
END

-- Use of this module defined in SAE J2735
-- This standard is not released (WIP)
-- Filename: J2735-TSPAT-2024-ph-v1.1.asn
--
-- Note: This is a *placeholder* file for the fully defined ASN.1 module.
-- Replace this file with the correct SAE file to compile a functional module.
--

TrafficSignalPhaseAndTiming
{joint-iso-itu-t (2) country (16) us (840) organization (1) sae (114566)
v2x-communications (1) technical-committees (1) v2x-core (5) technical-reports (1)
j2735 (2735) part-0 (0) asn1-module (1) trafficSignalPhaseAndTiming (45)
version-1 (1) version-minor-1 (1)}

DEFINITIONS AUTOMATIC TAGS ::=
BEGIN

TrafficSignalPhaseAndTiming ::= NULL

END-- Use of this module defined in SAE J2735
-- Latest document release for this module is Nov 2022
-- Filename: J2735-TestMessages-2024-rel-v1.1.asn
--
-- Note: This module contains ASN.1 entities for TestMessage00 - TestMessage15
--

TestMessage00
{joint-iso-itu-t (2) country (16) us (840) organization (1) sae (114566)
v2x-communications (1) technical-committees (1) v2x-core (5) technical-reports (1)
j2735 (2735) part-0 (0) asn1-module (1) testMessage00 (22) version-1 (1) version-minor-1 (1)}

DEFINITIONS AUTOMATIC TAGS ::=
BEGIN

IMPORTS
   Reg-TestMessage00
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage00 ::= SEQUENCE {
   header    Header   OPTIONAL,
   regional  RegionalExtension {{Reg-TestMessage00}} OPTIONAL,
   ...
   }
END

TestMessage01
{joint-iso-itu-t (2) country (16) us (840) organization (1) sae (114566)
v2x-communications (1) technical-committees (1) v2x-core (5) technical-reports (1)
j2735 (2735) part-0 (0) asn1-module (1) testMessage01 (23) version-1 (1) version-minor-1 (1)}
DEFINITIONS AUTOMATIC TAGS ::=
BEGIN

IMPORTS
   Reg-TestMessage01
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage01 ::= SEQUENCE {
   header    Header   OPTIONAL,
   regional  RegionalExtension {{Reg-TestMessage01}} OPTIONAL,
   ...
   }
END

TestMessage02
{joint-iso-itu-t (2) country (16) us (840) organization (1) sae (114566)
v2x-communications (1) technical-committees (1) v2x-core (5) technical-reports (1)
j2735 (2735) part-0 (0) asn1-module (1) testMessage02 (24) version-1 (1) version-minor-1 (1)}
DEFINITIONS AUTOMATIC TAGS ::=
BEGIN

IMPORTS
   Reg-TestMessage02
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage02 ::= SEQUENCE {
   header    Header   OPTIONAL,
   regional  RegionalExtension {{Reg-TestMessage02}} OPTIONAL,
   ...
   }
END

TestMessage03
{joint-iso-itu-t (2) country (16) us (840) organization (1) sae (114566)
v2x-communications (1) technical-committees (1) v2x-core (5) technical-reports (1)
j2735 (2735) part-0 (0) asn1-module (1) testMessage03 (25) version-1 (1) version-minor-1 (1)}
DEFINITIONS AUTOMATIC TAGS ::=
BEGIN

IMPORTS
   Reg-TestMessage03
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage03 ::= SEQUENCE {
   header    Header   OPTIONAL,
   regional  RegionalExtension {{Reg-TestMessage03}} OPTIONAL,
   ...
   }
END

TestMessage04
{joint-iso-itu-t (2) country (16) us (840) organization (1) sae (114566)
v2x-communications (1) technical-committees (1) v2x-core (5) technical-reports (1)
j2735 (2735) part-0 (0) asn1-module (1) testMessage04 (26) version-1 (1) version-minor-1 (1)}
DEFINITIONS AUTOMATIC TAGS ::=
BEGIN

IMPORTS
   Reg-TestMessage04
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage04 ::= SEQUENCE {
   header    Header   OPTIONAL,
   regional  RegionalExtension {{Reg-TestMessage04}} OPTIONAL,
   ...
   }
END

TestMessage05
{joint-iso-itu-t (2) country (16) us (840) organization (1) sae (114566)
v2x-communications (1) technical-committees (1) v2x-core (5) technical-reports (1)
j2735 (2735) part-0 (0) asn1-module (1) testMessage05 (27) version-1 (1) version-minor-1 (1)}
DEFINITIONS AUTOMATIC TAGS ::=
BEGIN

IMPORTS
   Reg-TestMessage05
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage05 ::= SEQUENCE {
   header    Header   OPTIONAL,
   regional  RegionalExtension {{Reg-TestMessage05}} OPTIONAL,
   ...
   }
END

TestMessage06
{joint-iso-itu-t (2) country (16) us (840) organization (1) sae (114566)
v2x-communications (1) technical-committees (1) v2x-core (5) technical-reports (1)
j2735 (2735) part-0 (0) asn1-module (1) testMessage06 (28) version-1 (1) version-minor-1 (1)}
DEFINITIONS AUTOMATIC TAGS ::=
BEGIN

IMPORTS
   Reg-TestMessage06
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage06 ::= SEQUENCE {
   header    Header   OPTIONAL,
   regional  RegionalExtension {{Reg-TestMessage06}} OPTIONAL,
   ...
   }
END

TestMessage07
{joint-iso-itu-t (2) country (16) us (840) organization (1) sae (114566)
v2x-communications (1) technical-committees (1) v2x-core (5) technical-reports (1)
j2735 (2735) part-0 (0) asn1-module (1) testMessage07 (29) version-1 (1) version-minor-1 (1)}
DEFINITIONS AUTOMATIC TAGS ::=
BEGIN

IMPORTS
   Reg-TestMessage07
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage07 ::= SEQUENCE {
   header    Header   OPTIONAL,
   regional  RegionalExtension {{Reg-TestMessage07}} OPTIONAL,
   ...
   }
END

TestMessage08
{joint-iso-itu-t (2) country (16) us (840) organization (1) sae (114566)
v2x-communications (1) technical-committees (1) v2x-core (5) technical-reports (1)
j2735 (2735) part-0 (0) asn1-module (1) testMessage08 (30) version-1 (1) version-minor-1 (1)}
DEFINITIONS AUTOMATIC TAGS ::=
BEGIN

IMPORTS
   Reg-TestMessage08
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage08 ::= SEQUENCE {
   header    Header   OPTIONAL,
   regional  RegionalExtension {{Reg-TestMessage08}} OPTIONAL,
   ...
   }
END

TestMessage09
{joint-iso-itu-t (2) country (16) us (840) organization (1) sae (114566)
v2x-communications (1) technical-committees (1) v2x-core (5) technical-reports (1)
j2735 (2735) part-0 (0) asn1-module (1) testMessage09 (31) version-1 (1) version-minor-1 (1)}
DEFINITIONS AUTOMATIC TAGS ::=
BEGIN

IMPORTS
   Reg-TestMessage09
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage09 ::= SEQUENCE {
   header    Header   OPTIONAL,
   regional  RegionalExtension {{Reg-TestMessage09}} OPTIONAL,
   ...
   }
END

TestMessage10
{joint-iso-itu-t (2) country (16) us (840) organization (1) sae (114566)
v2x-communications (1) technical-committees (1) v2x-core (5) technical-reports (1)
j2735 (2735) part-0 (0) asn1-module (1) testMessage10 (32) version-1 (1) version-minor-1 (1)}
DEFINITIONS AUTOMATIC TAGS ::=
BEGIN

IMPORTS
   Reg-TestMessage10
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage10 ::= SEQUENCE {
   header    Header   OPTIONAL,
   regional  RegionalExtension {{Reg-TestMessage10}} OPTIONAL,
   ...
   }
END

TestMessage11
{joint-iso-itu-t (2) country (16) us (840) organization (1) sae (114566)
v2x-communications (1) technical-committees (1) v2x-core (5) technical-reports (1)
j2735 (2735) part-0 (0) asn1-module (1) testMessage11 (33) version-1 (1) version-minor-1 (1)}
DEFINITIONS AUTOMATIC TAGS ::=
BEGIN

IMPORTS
   Reg-TestMessage11
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage11 ::= SEQUENCE {
   header    Header   OPTIONAL,
   regional  RegionalExtension {{Reg-TestMessage11}} OPTIONAL,
   ...
   }
END

TestMessage12
{joint-iso-itu-t (2) country (16) us (840) organization (1) sae (114566)
v2x-communications (1) technical-committees (1) v2x-core (5) technical-reports (1)
j2735 (2735) part-0 (0) asn1-module (1) testMessage12 (34) version-1 (1) version-minor-1 (1)}
DEFINITIONS AUTOMATIC TAGS ::=
BEGIN

IMPORTS
   Reg-TestMessage12
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage12 ::= SEQUENCE {
   header    Header   OPTIONAL,
   regional  RegionalExtension {{Reg-TestMessage12}} OPTIONAL,
   ...
   }
END

TestMessage13
{joint-iso-itu-t (2) country (16) us (840) organization (1) sae (114566)
v2x-communications (1) technical-committees (1) v2x-core (5) technical-reports (1)
j2735 (2735) part-0 (0) asn1-module (1) testMessage13 (35) version-1 (1) version-minor-1 (1)}
DEFINITIONS AUTOMATIC TAGS ::=
BEGIN

IMPORTS
   Reg-TestMessage13
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage13 ::= SEQUENCE {
   header    Header   OPTIONAL,
   regional  RegionalExtension {{Reg-TestMessage13}} OPTIONAL,
   ...
   }
END

TestMessage14
{joint-iso-itu-t (2) country (16) us (840) organization (1) sae (114566)
v2x-communications (1) technical-committees (1) v2x-core (5) technical-reports (1)
j2735 (2735) part-0 (0) asn1-module (1) testMessage14 (36) version-1 (1) version-minor-1 (1)}
DEFINITIONS AUTOMATIC TAGS ::=
BEGIN

IMPORTS
   Reg-TestMessage14
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage14 ::= SEQUENCE {
   header    Header   OPTIONAL,
   regional  RegionalExtension {{Reg-TestMessage14}} OPTIONAL,
   ...
   }
END

TestMessage15
{joint-iso-itu-t (2) country (16) us (840) organization (1) sae (114566)
v2x-communications (1) technical-committees (1) v2x-core (5) technical-reports (1)
j2735 (2735) part-0 (0) asn1-module (1) testMessage15 (37) version-1 (1) version-minor-1 (1)}
DEFINITIONS AUTOMATIC TAGS ::=
BEGIN

IMPORTS
   Reg-TestMessage15
      FROM REGION {joint-iso-itu-t (2) country (16) us (840) organization (1) sae (114566)
      v2x-communications (1) technical-committees (1) v2x-core (5) technical-reports (1)
      j2735 (2735) part-0 (0) asn1-module (1) region (2)
      version-1 (1) version-minor-1 (1)}
   Header,
   RegionalExtension
      FROM Common {joint-iso-itu-t (2) country (16) us (840) organization (1) sae (114566)
      v2x-communications (1) technical-committees (1) v2x-core (5) technical-reports (1)
      j2735 (2735) part-0 (0) asn1-module (1) common (38)
      version-1 (1) version-minor-1 (1)};

TestMessage15 ::= SEQUENCE {
   header    Header   OPTIONAL,
   regional  RegionalExtension {{Reg-TestMessage15}} OPTIONAL,
   ...
   }
END
-- Use of this module defined in SAE J2945/3
-- Latest document release for this module is Jan 2022
-- Filename: J2945-3-RoadWeatherMessage-2024-rel-v2.1.asn
--

RoadWeatherMessage
{joint-iso-itu-t (2) country (16) us (840) organization (1) sae (114566)
v2x-communications (1) technical-committees (1) v2x-core (5) technical-reports (1)
j2945 (2945) slash-3 (3) asn1-module (1) roadWeatherMessage (0)
version-2 (2) version-minor-1 (1)}

DEFINITIONS AUTOMATIC TAGS ::=
BEGIN

IMPORTS
   VehicleStatus
      FROM ProbeVehicleData {joint-iso-itu-t (2) country (16) us (840) organization (1) sae (114566)
      v2x-communications (1) technical-committees (1) v2x-core (5) technical-reports (1)
      j2735 (2735) part-0 (0) asn1-module (1) probeVehicleData (15)
      version-1 (1) version-minor-1 (1)}

   FullPositionVector,
   RoadRoughness,
   VehicleSafetyExtensions
      FROM Common {joint-iso-itu-t (2) country (16) us (840) organization (1) sae (114566)
      v2x-communications (1) technical-committees (1) v2x-core (5) technical-reports (1)
      j2735 (2735) part-0 (0) asn1-module (1) common (38)
      version-1 (1) version-minor-1 (1)}

   TravelerDataFrameList
      FROM TravelerInformation {joint-iso-itu-t (2) country (16) us (840) organization (1) sae (114566)
      v2x-communications (1) technical-committees (1) v2x-core (5) technical-reports (1)
      j2735 (2735) part-0 (0) asn1-module (1) travelerInformation (20)
      version-1 (1) version-minor-1 (1)}

   ITIStext
      FROM ITIS {joint-iso-itu-t (2) country (16) us (840) organization (1) sae (114566)
      v2x-communications (1) technical-committees (1) v2x-core (5) technical-reports (1)
      j2735 (2735) part-0 (0) asn1-module (1) itis (6)
      version-1 (1) version-minor-1 (1)};

--
-- Data elements that begin with "NTCIP" (all caps) are derived from NTCIP
-- 1204 v04 MIB objects.
-- For example, the data element name "NTCIPEssPavementTreatmentLatitude"
-- corresponds with the MIB entry "essPavementTreatmentLatitude".
-- See NTCIP 1204 v04 for additional information.
--

RoadWeatherMessage ::= CHOICE {
    upload    RoadWeatherUpload,
    download  RoadWeatherDownload,
    ...
}

-- Upload messages are sent from vehicles to infrastructure
RoadWeatherUpload ::= CHOICE {
    vehicleReport   SEQUENCE (SIZE(1..32)) OF VehicleReport,
    citizenReport   SnapShot,
    ...
}

VehicleReport ::= SEQUENCE {
    snapShot         SnapShot,
    wdmsFleetData    WDMSFleetData      OPTIONAL,
    ...
}

-- Download messages are sent from infrastructure to vehicles
RoadWeatherDownload ::= SEQUENCE {
    travelerData    TravelerDataFrameList,
    wdmsFleetData   WDMSFleetData OPTIONAL,
    ...
}

WDMSFleetData ::= SEQUENCE {
    pavementTreat   NtcipPavementTreatment  OPTIONAL,
    routingAdvice   ITIStext           OPTIONAL,
    ...
}

NtcipPavementTreatment ::= SEQUENCE {
    latitude    NTCIPEssPavementTreatmentLatitude,
    longitude   NTCIPEssPavementTreatmentLongitude,
    location    NTCIPEssPavementTreatmentLocation,
    productType NTCIPEssPaveTreatProductType        OPTIONAL,
    form        NTCIPEssPaveTreatProductForm        OPTIONAL,
    percentage  NTCIPEssPercentProductMix           OPTIONAL,
    amount      NTCIPEssPaveTreatmentAmount         OPTIONAL,
    width       NTCIPEssPaveTreatmentWidth          OPTIONAL,
    ...
}

NTCIPEssPavementTreatmentLatitude ::= INTEGER (-90000000..90000001)
    -- The latitude in 10^-6 degrees of the pavement treatment system, per
    -- WGS-84 datum

NTCIPEssPavementTreatmentLongitude ::= INTEGER (-180000000..180000001)
    -- The east longitude in 10^-6 degrees from the Prime Meridian of the
    -- pavement treatment system location

NTCIPEssPavementTreatmentLocation ::= IA5String (SIZE(1..255))
    -- A textual string indicating the location of the pavement treatment
    -- system

NTCIPEssPaveTreatProductType ::= ENUMERATED {
    -- Indicates the type of treatment being applied to the road.
    other (1),          -- any other type of treatment
    sand (2),
    dirt (3),
    gravel (4),
    cinders (5),
    water (6),          -- used as a diluting agent
    enhancedSalts (7),
    naCl (8),
    caCl (9),
    mgCl (10),
    cMA (11),           -- Calcium-Magnesium Acetate
    kAC (12),           -- Potassium-Magnesium Acetate
    naFormate (13),     -- Sodium Formate
    naA (14),           -- Sodium Acetate
    ...
}

NTCIPEssPaveTreatProductForm ::= ENUMERATED {
    -- Indicates the condition of the treatment being applied to the road
    other (1),
    dry (2),
    prewet (3),
    liquid (4),
    ...
}

NTCIPEssPercentProductMix ::= INTEGER (0..100)
    -- Indicates the percentage of the total application mix by weight that
    -- is of the type specified in essPaveTreatProductType

NTCIPEssPaveTreatmentAmount ::= INTEGER (0..255)
    -- Indicates quantity of the treatment being applied in kilograms per
    -- lane kilometer

NTCIPEssPaveTreatmentWidth ::= INTEGER (0..255)
    -- Indicates the width of the spread of treatment in meters


SnapShot ::= SEQUENCE {
    thePosition     FullPositionVector,
        -- data of the position and speed,
    safetyExt       VehicleSafetyExtensions    OPTIONAL,
    dataSet         VehicleStatus              OPTIONAL,
        -- a sequence of data frames which encodes the data
    ...,
    weatherData     NtcipEssData                    OPTIONAL
        -- Added by J2945/3
}

NtcipEssData ::= SEQUENCE {
    airTemp         NtcipAirTemperature         OPTIONAL,
    atmosphere      NtcipAtmosphericPressure    OPTIONAL,
    wind            NtcipWind                   OPTIONAL,
    humidity        NtcipRelativeHumidity       OPTIONAL,
    dewpoint        NtcipDewPoint               OPTIONAL,
    pavement        NtcipPavement               OPTIONAL,
    visibility      NtcipVisibility             OPTIONAL,
    visSituation    NtcipVisibilitySituation    OPTIONAL,
    cloudSitiation  NtcipCloudSituation         OPTIONAL,
    precipitation   NtcipPrecipitation          OPTIONAL,
    solarRadiation  NtcipSolarRadiation         OPTIONAL,
    ...
}

NtcipAirTemperature ::= SEQUENCE {
    temperature         NTCIPEssAirTemperature,
    measurementStdDev   TemperatureMeasurementStdDev    OPTIONAL,
    tempSensorHeight    NTCIPEssTemperatureSensorHeight OPTIONAL,
    ...
}

NTCIPEssAirTemperature ::= INTEGER (-1000..1001)
    -- The dry-bulb temperature in tenths of degrees Celsius. The
    -- temperature is an instantaneous reading at the height specified
    -- by essTemperatureSensorHeight

NTCIPEssTemperatureSensorHeight ::= INTEGER (-1000..1001)
    -- The height of the temperature sensor as measured in meters
    -- above essReferenceHeight

NtcipAtmosphericPressure ::= SEQUENCE {
    pressure          NTCIPEssPressureSensorAtmosphericPressure,
    measurementStdDev AtmosPressureMeasurementStdDev  OPTIONAL,
    ...
}

NTCIPEssPressureSensorAtmosphericPressure ::= INTEGER (0..65535)
    -- The force per unit area exerted by the atmosphere in 1/10ths of
    -- millibars, a.k.a. tenths of hectoPascals

NtcipWind ::= SEQUENCE {
    avgSpeed        NTCIPWindSensorAvgSpeed         OPTIONAL,
    avgDirection    NTCIPWindSensorAvgDirection     OPTIONAL,
    currentSpeed    NTCIPWindSensorSpotSpeed        OPTIONAL,
    curDirection    NTCIPWindSensorSpotDirection    OPTIONAL,
    gustSpeed       NTCIPWindSensorGustSpeed        OPTIONAL,
    gustDirection   NTCIPWindSensorGustDirection    OPTIONAL,
    ...
}

NTCIPWindSensorAvgSpeed ::= INTEGER (0..65535)
    -- A two minute average of the wind speed in tenths of
    -- meters per second as measured by the wind sensor

NTCIPWindSensorAvgDirection ::= INTEGER (0..361)
    -- A two minute mode (average) of the direction from which the wind is
    -- blowing measured clockwise in degrees from true north as measured
    -- by the wind sensor

NTCIPWindSensorSpotSpeed ::= INTEGER (0..65535)
    -- Definition>The wind speed in tenths of meters per second measured by
    -- the wind sensor. For mobile platforms, the wind speed shall be
    -- corrected for vehicle movement

NTCIPWindSensorSpotDirection ::= INTEGER (0..361)
    -- The direction from which the wind is blowing measured in
    -- degrees clockwise from true North as measured by the wind sensor.
    -- For mobile platforms, the wind direction shall be corrected for
    -- vehicle movement

NTCIPWindSensorGustSpeed ::= INTEGER (0..65535)
    -- The maximum wind gust recorded by the wind sensor during
    -- the 10 minutes preceding the observation measured in tenths of
    -- meters per second

NTCIPWindSensorGustDirection ::= INTEGER (0..361)
    -- The direction of the maximum wind gust recorded during the 10
    -- minutes preceding the observation measured in degrees clockwise
    -- from true North by the wind sensor.

NtcipRelativeHumidity ::= SEQUENCE {
    relHumidity     NTCIPHumiditySensorRelativeHumidity,
    source          DataSourceInfo                  OPTIONAL,
    ...
}

NTCIPHumiditySensorRelativeHumidity ::= INTEGER (0..101)
    -- The relative humidity in percent

NtcipDewPoint ::= SEQUENCE {
    dewTemp           NTCIPEssDewpointTemp,
    source            DataSourceInfo                  OPTIONAL,
    measurementStdDev DewPointTempMeasurementStdDev   OPTIONAL,
    ...
}

NTCIPEssDewpointTemp ::= INTEGER (-1000..1001)
    -- The dewpoint temperature in tenths of degrees Celsius. The
    -- temperature is an instantaneous reading by the temperature
    -- sensor specified in the first row specified of the
    -- essTemperatureSensorTable

NtcipPavement ::= SEQUENCE {
    surfaceTemp          NTCIPEssSurfaceTemperature             OPTIONAL,
    tempStdDev           SurfaceTempMeasurementStdDev           OPTIONAL,
    condition            NTCIPPavementSensorSurfaceCondition    OPTIONAL,
    moistureDepth        NTCIPEssSurfaceIceOrWaterDepth         OPTIONAL,
    roadRoughness        RoadRoughness                           OPTIONAL,
    ...
}

NTCIPEssSurfaceTemperature ::= INTEGER (-1000..1001)
    -- The current pavement surface temperature in tenths of degrees Celsius

NTCIPPavementSensorSurfaceCondition ::= ENUMERATED {
    -- A value indicating the pavement surface status
    other (1),
    error (2),
    dry (3),
    moist (4),
    chemicallyMoist(5),
    wet (6),
    chemicallyWet (7),
    standingWater (8),
    frost (9),
    slush (10),
    snow (11),
    ice (12),
    noReport (13),
    ...
}

NTCIPEssSurfaceIceOrWaterDepth ::= INTEGER (0..65535)
    -- The current thickness of ice or depth of water on the surface of the
    -- roadway measured in 1/10th of millimeters

NtcipVisibility::= SEQUENCE {
    visibility      NTCIPEssVisibility,
    ...
}

NTCIPEssVisibility ::= INTEGER (0..1000001)
    -- Surface visibility measured in one tenth of a meter


NtcipVisibilitySituation::= SEQUENCE {
    situation       NTCIPEssVisibilitySituation,
    ...
}

NTCIPEssVisibilitySituation ::= ENUMERATED {
    -- Describes the travel environment in terms of visibility. If one
    -- exists, the corresponding BUFR value is indicated for staffed
    -- (BUFRs) and automated (BUFRa) stations. The indicated value can
    -- be found in the BUFR Table referenced in NTCIP 1204 v04.23
    other (1),
    unknown (2),
    clear (3),
    fogNotPatchy (4),
    patchyFog (5),
    blowingSnow (6),
    smoke (7),
    seaSpray (8),
    vehicleSpray (9),
    blowingDustOrSand (10),
    sunGlare (11),
    swarmsOfInsects (12),
    ...
}

NtcipCloudSituation::= SEQUENCE {
    situation       NTCIPEssCloudSituationV4,
    ...
}

NTCIPEssCloudSituationV4 ::= INTEGER (0..8)
    -- Describes the amount of cloud cover in the sky, measured in oktas,
    -- as defined in WMO code table 2700

NtcipPrecipitation::= SEQUENCE {
    precipitation       NTCIPPrecipitationSensorPrecipSituation,
    ...
}

NTCIPPrecipitationSensorPrecipSituation ::= ENUMERATED {
    -- Describes the weather situation in terms of precipitation. For
    -- automated stations, describes the intensity and precipitation type
    -- as specified in the first row of the precipitationSensorTable
    other (1),
    unknown (2),
    noPrecipitation (3),
    unidentifiedSlight (4),
    unidentifiedModerate (5),
    unidentifiedHeavy (6),
    snowSlight (7),
    snowModerate (8),
    snowHeavy (9),
    rainSlight (10),
    rainModerate (11),
    rainHeavy (12),
    frozenPrecipitationSlight (13),
    frozenPrecipitationModerate (14),
    frozenPrecipitationHeavy (15),
    ...
}

NtcipSolarRadiation ::= SEQUENCE {
    solarRadiation      NTCIPEssTotalRadiationV4,
    measurementPeriod   NTCIPEssTotalRadiationPeriod,
    ...
}

NTCIPEssTotalRadiationV4 ::= INTEGER (-2048..2049)
    -- The average total radiation hitting the earth's surface in watts per
    -- square meter during the radiation period

NTCIPEssTotalRadiationPeriod ::= INTEGER (0..86400)
    -- The rolling period, in seconds, that corresponds to the length of
    -- time the essTotalRadiation is averaged

TemperatureMeasurementStdDev ::= INTEGER (1..16)
    -- standard deviation in degrees

AtmosPressureMeasurementStdDev ::= INTEGER (1..16)
    --standard deviation in tenths of hPa

DewPointTempMeasurementStdDev ::= INTEGER (1..16)
    --standard deviation in degrees

SurfaceTempMeasurementStdDev ::= INTEGER (1..16)
    --standard deviation in degrees

DataSourceInfo ::= ENUMERATED { measured, derived, ... }
    -- Indicates source of the data

END

-- Use of this module defined in SAE J2945/4
-- Latest document release for this module is May 2023
-- Filename: J2945-4-RoadSafetyMessage-2024-rel-v1.1.1.asn
--

RoadSafetyMessage
{joint-iso-itu-t (2) country (16) us (840) organization (1) sae (114566)
v2x-communications (1) technical-committees (1) v2x-core (5) technical-reports (1)
j2945 (2945) slash-4 (4) asn1-module (1) roadSafetyMessage (39)
version-1 (1) version-minor-1 (1)}

DEFINITIONS AUTOMATIC TAGS ::=
BEGIN

IMPORTS
    DDate,
    DDateTime,
    DescriptiveName,
    DTime,
    FrictionInformation,
    MsgCount,
    ObstacleDistance,
    Position3D,
    RegulatorySpeedLimit,
    RoadAuthorityID,
    TemporaryID
        FROM Common {joint-iso-itu-t (2) country (16) us (840) organization (1)
        sae (114566) v2x-communications (1) technical-committees (1) v2x-core (5)
        technical-reports (1) j2735 (2735) part-0 (0) asn1-module (1) common (38)
        version-1 (1) version-minor-1 (1)}
    SpeedAdvice
        FROM SPAT {joint-iso-itu-t (2) country (16) us (840) organization (1)
        sae (114566) v2x-communications (1) technical-committees (1) v2x-core (5)
        technical-reports (1) j2735 (2735) part-0 (0) asn1-module (1)
        signalPhaseAndTimingMessage (9)
      version-1 (1) version-minor-1 (1)}
    Circle,
    Zoom
        FROM TravelerInformation {joint-iso-itu-t (2) country (16) us (840) organization (1)
      sae (114566) v2x-communications (1) technical-committees (1) v2x-core (5)
      technical-reports (1) j2735 (2735) part-0 (0) asn1-module (1) travelerInformation (20)
      version-1 (1) version-minor-1 (1)}
    NTCIPEssVisibility
        FROM RoadWeatherMessage {joint-iso-itu-t (2) country (16) us (840) organization (1)
      sae (114566) v2x-communications (1) technical-committees (1)
        v2x-core (5) technical-reports (1) j2945 (2945) slash-3 (3)
        asn1-module (1) roadWeatherMessage (0)
      version-2 (2) version-minor-1 (1)}
    ITISResponderGroupAffected,
    ITIScodes,
    ITISVehicleGroupAffected
        FROM ITIS {joint-iso-itu-t (2) country (16) us (840) organization (1)
        sae (114566) v2x-communications (1) technical-committees (1) v2x-core (5)
        technical-reports (1) j2735 (2735) part-0 (0) asn1-module (1) itis (6)
        version-1 (1) version-minor-1 (1)}
    ITISgroups
        FROM J2540ITIS {joint-iso-itu-t(2) country(16) us(840) organization(1)
      sae(114566) v2x-communications(1) technical-committees(1) v2x-core(5)
      standards(1) itis-phrase-lists(2540) part-2(2) asn1(1)
      major-version-1(1) minor-version-1 (1)};

-- Road Safety Message is abbreviated as RSM in type definitions and comments below
RoadSafetyMessage ::= SEQUENCE {
    -- This mandatory container describes generic information about the event.
    commonContainer     CommonContainer,

    -- up to 4 application content containers, may be repeated or different ones
    content             SEQUENCE (SIZE(1..4)) OF ContentContainer,
    ...
}

-- CommonContainer is mandatory and applies to all RSMs
CommonContainer ::= SEQUENCE {
    eventInfo         EventInfo,
    -- Includes eventID, start/end date/times, eventRecurrance, causeCodes
    regionInfo        SEQUENCE      (SIZE(1..4)) OF RegionInfo,
    -- Includes referencePoint, applicableHeading, roadWidth (pathWidth), approachLanes (approachRegion)
    crossLinking      CrossLinking  OPTIONAL,
    -- Allows linking to other messages or content
    ...
}

ContentContainer ::= CHOICE {
    -- The following application containers describe use-case specific
    -- information about the event.
    rszContainer           ReducedSpeedZoneContainer,
    laneClosureContainer   LaneClosureContainer,
    curveContainer         CurveContainer,
    dynamicInfoContainer   DynamicInfoContainer,
    -- Traditional "DMS"-type display
    incidentsContainer     IncidentsContainer,
    -- Typically collisions or point-based disruptions
    situationalContainer   SituationalContainer,
    -- This contains situational information that may apply to multiple applications
    ...
}

-- Optional container describing conditions that may be present in a curve of the roadway
CurveContainer ::= SEQUENCE {
    advisorySpeed     SpeedAdvice,
    -- Recommended speed limit for the curve
    surfaceCondition  FrictionInformation   OPTIONAL,
    -- Data describing the surface conditions of the road
    minRadius         Radius                OPTIONAL,
    -- Minimum radius of the curve in meters
    bankAngle         BankAngle             OPTIONAL,
    -- Maximum (most extreme) bank angle present along the curve
    curveRegion       RegionInfo            OPTIONAL,
    -- Describes geometry of lanes or polygon in the curve
    ...
}

-- Context provided by CommonContainer codes
DynamicInfoContainer ::= SEQUENCE {
    priority          ENUMERATED {low-priority      (0),
                                  medium-priority   (1),
                                  high-priority     (2),
                                  critical          (3)},
    dmsSignString     SEQUENCE SIZE(1..12) OF ShortString,
    applicableRegion  RegionInfo,    -- The location/region for which the information applies
    ...
}

IncidentsContainer ::= SEQUENCE {
    responderType       SEQUENCE (SIZE(1..5)) OF ITISResponderGroupAffected OPTIONAL,
    incidentLocation    RegionInfo,      -- May be a point (circle with 0 radius, or a small radius)
    ...
}

LaneClosureContainer ::= SEQUENCE {
    laneStatus          SEQUENCE (SIZE(1..10, ...)) OF LaneInfo OPTIONAL,
    -- Lane status (open/closed) and closure offset from ref point
    laneStatusVaries    Activity    OPTIONAL,
    -- An indication that specific lanes that are closed may vary over the duration
    closureRegion       RegionInfo,
    ...
}

-- Optional container describing a zone where reduced speed is required, maybe a workzone or
-- other type of zone (e.g., school).
-- Abbreviated as rsz or RSZ in various comments and type definitions below.
ReducedSpeedZoneContainer ::= SEQUENCE {
    speedLimit          RegulatorySpeedLimit,   -- Speed limit associated with event
    rszRegion           RegionInfo,             -- Describes region of reduced speed zone
    ...
}

-- Provides situaltional awareness that applies to multiple other application specific containers
SituationalContainer ::= SEQUENCE {
    obstructions        Obstructions          OPTIONAL,     -- Location, size
    visibility          NTCIPEssVisibility    OPTIONAL,     -- An estimate of the surface visibility
    peoplePresent       Activity              OPTIONAL,
    -- An indication that pedestrians are expected to be present (workers in a construction zone,
    -- children in a school zone, etc)
    anomalousTraffic    Activity              OPTIONAL,
    -- An indication that vehicles may be on, entering, or leaving the roadway
    applicableRegion    RegionInfo,
    -- The location/region for which the information applies
    ...
}

-- Frames

ApplicableHeading ::= SEQUENCE {
    heading         HeadingDeg,
    -- Heading in 1 degree increments, message applies to heading +/- tolerance
    tolerance       Tolerance,
    -- Tolerance in 1 degree increments
    ...
}

-- Provides choice of methods to describe a region, i.e., lane based or other more general region
-- definitions (e.g. polygon, etc.)
AreaType ::= CHOICE {
    broadRegion     BroadRegion,    -- Polygon or Circle
    paths           PathList,       -- One or more coarse "lanes" (or roads) with a width
    ...
}

AudioLink ::= SEQUENCE {
    amChannel           INTEGER (531..1710)        OPTIONAL,
    fmChannel           INTEGER (65800..108009)    OPTIONAL,
    satelliteChannel    INTEGER (1..9999)          OPTIONAL,
    urlChannel          IA5String (SIZE(1..500))   OPTIONAL,
    ...
}

BroadRegion ::= SEQUENCE {
    applicableHeading   ApplicableHeading,
    -- Provide so map matching algs can easily determine direction of travel
    broadArea           BroadRegionArea,
    ...
}

BroadRegionArea ::= CHOICE {
    polygon            RSMPolygon,
    circle             Circle,
    ...
}

CrossLinking ::= SEQUENCE {
    audioLinks      SEQUENCE (SIZE(1..4, ...)) OF AudioLink         OPTIONAL,
    visualLink      SEQUENCE (SIZE(1..4, ...)) OF VisualLink        OPTIONAL,
    rsmLink         SEQUENCE (SIZE(1..4, ...)) OF EventIdentifier   OPTIONAL,
    ...
}

EventIdentifier ::= SEQUENCE {
    operatorID      RoadAuthorityID,    -- A globally unique regional assignment value
                                        -- typically assigned to a regional DOT authority
    uniqueID        TemporaryID,        -- A unique ID assigned to the event by the operator
    ...
}

-- Contains info related to event start/end date/times, recurrence, cause codes
EventInfo ::= SEQUENCE {
    eventID           EventIdentifier,                  -- Uniquely assigned ID for this event
    eventUpdate       MsgCount,
    -- An incrementing revision number to indicate changes to a previous transmission of this information
    eventCancellation Activity,
    -- A flag indicating that this event has been cancelled (in particular, prior to the indicated endTime)
    startDateTime     DDateTime,                        -- Event start date and time
    endDateTime       DDateTime        OPTIONAL,
    -- Event end date and time (applies to current message instance). Can be omitted if indefinite or
    -- unknown, can be used to calculate the validity time duration of the message.
    eventRecurrence   SEQUENCE (SIZE(1..5, ...)) OF EventRecurrence OPTIONAL,
    -- Indicates the date/time periods for which an event is active. Up to 5 periods may be defined
    causeCode         ITISgroups,                       -- List of possible events
    subCauseCode      ITIScodes        OPTIONAL,        -- List of possible events (use-case specific)
    affectedVehicles  SEQUENCE (SIZE(1..10, ...)) OF ITISVehicleGroupAffected OPTIONAL,
    -- List of affected vehicle classifications
    ...
}

-- Defines applicable periods for an event.
EventRecurrence ::= SEQUENCE {
    startTime   DTime  OPTIONAL,  -- Time of day this period starts
    endTime     DTime  OPTIONAL,  -- Time of day this period ends
    startDate   DDate  OPTIONAL,  -- Date this period starts
    endDate     DDate  OPTIONAL,  -- Date this period ends
    -- Define days of the week for applicable periods (used by EventRecurrence)
    monday      BOOLEAN,
    tuesday     BOOLEAN,
    wednesday   BOOLEAN,
    thursday    BOOLEAN,
    friday      BOOLEAN,
    saturday    BOOLEAN,
    sunday      BOOLEAN,
    exclusion   BOOLEAN     OPTIONAL,
    -- exclusion: TRUE: The period defined here is excluded, i.e., the period is NOT applicable
    -- to the event
    ...
}

-- For each lane, status (open/closed) and closure offset from reference point
LaneInfo ::= SEQUENCE {
    lanePosition      RSMLanePosition,            -- Where lanePosition 1 is always the leftmost lane
    laneClosed        LaneClosed,                 -- TRUE:lane closed, FALSE:lane open
    laneCloseOffset   ObstacleDistance OPTIONAL,  -- Distance from ref point to lane closure in meters
    ...
}

-- Replaces J2735's NodeOffsetPointXY in the RSM
NodePointLLE ::= CHOICE {
    -- Nodes with lat/long/elev content
    node-3Dabsolute   Position3D,       -- Absolute lat/long/elevation
    node-3Doffset     Offset3D,         -- Offsets of fractional deg (lat/long) and meters (elev)
    ...
}

Obstructions ::= SEQUENCE {
    location        Position3D,
    description     ITIScodes   OPTIONAL,
    ...
}

-- Provides lat/long/elev offsets from a known point
Offset3D ::= SEQUENCE {
    lat-offset      LatOffset,
    long-offset     LongOffset,
    elev-offset     ElevOffset    OPTIONAL,
    ...
}

Path ::= SEQUENCE {
    pathWidth       INTEGER (0..1000), -- Width of the Path in units of 10cm
    pathPoints      PathPoints,
    ...
}

PathList ::= SEQUENCE (SIZE(1..10), ...) OF Path

PathPoints ::= SEQUENCE (SIZE(2..63), ...) OF NodePointLLE

-- Contains info related to event heading, location, reference point, length
RegionInfo ::= SEQUENCE {
    referencePoint          Position3D,
    -- Reference position, may be start of event (default) or arbitrary location.
    locationUncertainty     RegionUncertainty      OPTIONAL,
    -- A measure of how accurate the region is known
    referencePointType      ReferencePointType     OPTIONAL,
    -- startOfEvent or arbitrary. If not provided, default to startOfEvent.
    descriptiveName         DescriptiveName        OPTIONAL,
    -- Plain text (human readable) name of roadway or region
    scale                   Zoom                   OPTIONAL,
    -- Used to scale offsets in the AreaType if necessary
    approachRegion          AreaType               OPTIONAL,
    -- Area preceding the location of the event, presumably where an alert/warning would be presented
    -- to a driver
    ...
}

RegionUncertainty ::= CHOICE {
    alongPath            Offset3D,      -- lateral/longitudinal
    inCoordinateFrame    Offset3D,      -- latitude/longitude
    ...
}

RSMPolygon ::= SEQUENCE (SIZE(3..63)) OF NodePointLLE -- May be defined by abs lat/lon/elev or offsets

VisualLink ::= SEQUENCE {
    urlLink IA5String (SIZE(1..500)) OPTIONAL,
    ...
}

-- ELEMENTS

Activity ::= BOOLEAN
-- TRUE: Relevant activity is occurring, FALSE: Relevant activity is not happening or inconclusive

-- Use scale (Zoom) to to modify the units for nodes' latitude and longitude (but not elevation).
-- For example the default units specified for latitude and longitude are tenths of microdegrees.
-- The scale factor is not applied to the elevation if present.
LatOffset  ::= INTEGER (-16384..16383) -- Offset 0.1 microdegrees (unless scale is provided)
LongOffset ::= INTEGER (-16384..16383) -- Offset 0.1 microdegrees (unless scale is provided)
ElevOffset ::= INTEGER (-4096..4095)   -- Offset in increments of 0.1 meters (scale not applied)

BankAngle ::= INTEGER (-512..512)  -- Tenths of degrees

HeadingDeg ::= INTEGER (0..359)  -- Heading in 1 degree increments, 0 = North, incrementing to the East

LaneClosed ::= BOOLEAN           -- TRUE: Lane is closed, FALSE: lane is not closed

Radius ::= INTEGER (0..65535)    -- Measured in meters

ReferencePointType ::= ENUMERATED {
    startOfEvent (0),
    arbitrary    (1),
    ...
}

RSMLanePosition ::= INTEGER (1..32) -- Lane position where lane 1 is always leftmost lane

ShortString ::= IA5String(SIZE(1..20))

Tolerance ::= INTEGER (0..180)  -- In 1 degree increments

END


-- Use of this module defined in SAE J2945/6
-- Latest document release for this module is Oct 2023
-- Filename: J2945-6-CooperativeControlMessage-2024-rel-v1.1.1.asn
--

CooperativeControlMessage
{joint-iso-itu-t (2) country (16) us (840) organization (1) sae (114566)
v2x-communications (1) technical-committees (1) v2x-vehicular-applications (8) technical-reports (1)
j2945 (2945) slash-6 (6) asn1-module (1) cooperativeControlMessage (40)
version-1 (1) version-minor-1 (1)}

DEFINITIONS AUTOMATIC TAGS ::=
BEGIN

IMPORTS
    VehicleSafetyExtensions
        FROM BasicSafetyMessage {joint-iso-itu-t (2) country (16) us (840) organization (1) sae (114566)
        v2x-communications (1) technical-committees (1) v2x-core (5) technical-reports (1)
        j2735 (2735) part-0 (0) asn1-module (1) basicSafetyMessage (7)
        version-1 (1)  version-minor-1 (1)}
    BSMcoreData,
    TemporaryID,
    Speed,
    Acceleration,
    YawRate
        FROM Common {joint-iso-itu-t (2) country (16) us (840) organization (1) sae (114566)
        v2x-communications (1) technical-committees (1) v2x-core (5) technical-reports (1)
        j2735 (2735) part-0 (0) asn1-module (1) common (38)
        version-1 (1) version-minor-1 (1)};

CooperativeControlMessage ::= SEQUENCE {
   -- Part I, Sent at all times with each message
   coreData      BSMcoreData,

   -- Part II Content
   partII        SEQUENCE (SIZE(1..8)) OF
                 CCMPartIIcontent {{ CCMpartIIExtension }} OPTIONAL,
   ...
   }

-- CCM Part II content support
CCMPARTII-EXT-ID-AND-TYPE ::= CLASS {
   &id     CCMPartII-Id UNIQUE,
   &Type
   } WITH SYNTAX {&Type IDENTIFIED BY &id}

CCMPartIIcontent  { CCMPARTII-EXT-ID-AND-TYPE: Set} ::= SEQUENCE {
   partII-Id     CCMPARTII-EXT-ID-AND-TYPE.&id( {Set} ),
   partII-Value  CCMPARTII-EXT-ID-AND-TYPE.&Type( {Set}{@partII-Id} )
   }

CCMPartII-Id ::= INTEGER (0..63)
   vehicleSafetyExt       CCMPartII-Id::= 0  -- VehicleSafetyExtensions
   lightVehicleCCMExt CCMPartII-Id::= 1  -- LightVehicleCCMExtensions
   heavyTruckCCMExt CCMPartII-Id::= 2  -- HeavyTruckCCMExtensions
   -- NOTE: new registered Part II content IDs will be denoted here


-- In a given message there may be multiple extensions present
-- but at most one instance of each extension type.
CCMpartIIExtension  CCMPARTII-EXT-ID-AND-TYPE ::= {
   { VehicleSafetyExtensions      IDENTIFIED BY vehicleSafetyExt} |
   { LightVehicleCCMExtensions    IDENTIFIED BY lightVehicleCCMExt} |
   { HeavyTruckCCMExtensions      IDENTIFIED BY heavyTruckCCMExt},
   ...
   }

LightVehicleCCMExtensions ::= SEQUENCE {
   longCntrlState     LongitudinalControlState,
   targetId           TemporaryID                 OPTIONAL,
   accelForecast      Acceleration                OPTIONAL,
   accelTimeConst     AccelTimeConstant           OPTIONAL,
   seperationDist     SeparationDistance          OPTIONAL,
   frontCutIn         FrontCutIn                  OPTIONAL,
   ...
   }

HeavyTruckCCMExtensions ::= SEQUENCE {
   longCntrlState            LongitudinalControlState,
   targetId                  TemporaryID                 OPTIONAL,
   roadGrade                 RoadGrade                   OPTIONAL,
   brakePedalPos             BrakePedalPosition          OPTIONAL,
   accelPedalPos             AcceleratorPedalPosition    OPTIONAL,
   desiredSpeed              Speed                       OPTIONAL,
   desiredAccel              Acceleration                OPTIONAL,
   desiredTorque             Torque                      OPTIONAL,
   desiredTmRetarderTorque   Torque                      OPTIONAL,
   desiredEngRetarderTorque  Torque                      OPTIONAL,
   axesMvmt                  AxesMovement                OPTIONAL,
   separationDist            SeparationDistance          OPTIONAL,
   totalMass                 TotalMass                   OPTIONAL,
   maxAvailAccel             MaxAvailableAcceleration    OPTIONAL,
   maxAvailDecel             MaxAvailableDeceleration    OPTIONAL,
   ccmFaultMode              CCMFaultMode                OPTIONAL,
   maneuverID                CCMManeuverID                  OPTIONAL,
   frontCutIn                FrontCutIn                  OPTIONAL,
   ...
   }

LongitudinalControlState ::= ENUMERATED {
    unavailable,
    manual,
    cc,
    acc,
    caccOne,
    caccMultiple,
    sensorAuto,
    fusedAuto,
    manualOver,
    ...
    } -- Note: subject to further growth

AccelTimeConstant ::= SEQUENCE {
   accelTimeConst     TimeConstant          OPTIONAL,
   decelTimeConst     TimeConstant          OPTIONAL
   }

TimeConstant ::= INTEGER (0..255) -- Units of 0.1 s
          -- Provides a range of 0 to 25.4 s
          -- The value 255 indicates unavailable

AxesMovement ::= SEQUENCE {
   yaw            Yaw            OPTIONAL,
   pitch          Pitch          OPTIONAL,
   roll           Roll           OPTIONAL,
   yawRate        YawRate        OPTIONAL,
   pitchRate      PitchRate      OPTIONAL,
   rollRate       RollRate       OPTIONAL
   }

RoadGrade ::= INTEGER (-100..101) -- LSB units are 0.2 percent
          -- Provides a range of -20 to 20 percent
          -- The value 101 indicates unavailable

BrakePedalPosition ::= INTEGER (0..201) -- LSB units are 0.5 percent
          -- Provides a range of 0 to 100 percent
          -- The value 201 indicates unavailable

AcceleratorPedalPosition ::= INTEGER (0..201) -- LSB units are 0.5 percent
          -- Provides a range of 0 to 100 percent
          -- The value 201 indicates unavailable

Torque ::= INTEGER (0..601) -- LSB units are 5 N-m
          -- Provides a range of 0 to 3000 N-m
          -- The value 601 indicates unavailable

Yaw ::= INTEGER (0..28800)
          -- LSB of 0.0125 degrees
          -- A range of 0 to 359.9875 degrees
          -- A value of 28800 shall be used when unavailable

Pitch ::= INTEGER (-7200..7201)
          -- LSB of 0.0125 degrees
          -- A range of -90 to 90 degrees
          -- A value of 7201 shall be used when unavailable

Roll ::= INTEGER (-7200..7201)
          -- LSB of 0.0125 degrees
          -- A range of -90 to 90 degrees
          -- A value of 7201 shall be used when unavailable

PitchRate ::= INTEGER (-3000..3001)
          -- LSB units of 0.01 degrees per second (signed)
          -- A value of 3001 shall be used when unavailable

RollRate ::= INTEGER (-3000..3001)
          -- LSB units of 0.01 degrees per second (signed)
          -- A value of 3001 shall be used when unavailable

SeparationDistance ::= INTEGER (0..2001) -- LSB units are 0.1 m
          -- Provides a range of 0 to 200 m
          -- The value 2001 indicates unavailable

TotalMass ::= INTEGER (0..1288) -- LSB units are 100 kg
          -- Provides a range of 0 to 128,600 kg
          -- The value 1287 for mass greater 128,600 kg
          -- The value 1288 indicates unavailable

MaxAvailableAcceleration ::= INTEGER (0..2001) -- LSB units are 0.01 m/s^2
          -- Provides a range of 0 to 20 m/s^2
          -- The value 2001 indicates unavailable

MaxAvailableDeceleration ::= INTEGER (-2001..0) -- LSB units are 0.01 m/s^2
          -- Provides a range of 0 to -20 m/s^2
          -- The value -2001 indicates unavailable

CCMFaultMode ::= BIT STRING {
    unavailable              (0),
    commFault                (1),
    radarFault               (2),
    lidarFault               (3),
    engingBrkCtlFault        (4),
    serviceBrkCtlFault       (5),
    transRetarderFault       (6),
    engineCtlFault           (7)
    } (SIZE (8, ...)) -- Note: subject to further growth


CCMManeuverID ::= INTEGER {
   unavailable                      (0),
   stayAtRestManCtl                 (1), -- Stay at rest with manual control
   stayAtRestAutoLonCtl             (2), -- Stay at rest with automatic
                                         --   longitudinal control
   autoSpdCtlFollowRefTrafAccel     (4), -- Automatic speed control following a
                                         --   reference trajectory b
                                         --   acceleration in response to speed
                                         --   limit change)
   transManToAutoSpdCtl             (5), -- Transition from manual to automatic
                                         --   speed control
   stringForm                       (6), -- Platoon forming - following the
                                         --   speed of the preceding vehicle in
                                         --   the platoon or CCM string, but
                                         --   not yet at the desired distance
                                         --   (speed tracking)
   autoJoinString                   (7), -- Automatic joining within a platoon
                                         --   or CCM string (speed & distance
                                         --   control to desired distance)
   autoCtl                          (8), -- Automatic platooning or CCM
                                         --   control (at cruise speed - no
                                         --   other maneuver)
   increaseGapAutoCtl               (9), -- Increasing gap under automatic
                                         --   control (within a platoon or CCM
                                         --   string) to a specified distance
                                         --   with respect to preceding vehicle
   leftLnChgEndString              (10), -- Left-lane-changing to the end of a
                                         --   platoon or CCM string
   rightLnChgEndString             (11), -- Right-lane-changing to the end of a
                                         --   platoon or CCM string
   virtualGapIncDiffLane           (12), -- Virtual gap increase to specified
                                         --   distance from current distance in
                                         --   a different lane
   virtualGapRedDiffLane           (13), -- Virtual gap reduction to specified
                                         --   distance from current distance in
                                         --   a different lane
   emgcyIncInterVehDistToStop      (14), -- Emergency increase to longer inter-
                                         --   vehicle distance to stop (due to
                                         --   an incurable fault)
   vehMrgToStringFrmOnramp         (15), -- Vehicle merging into a platoon or
                                         --   CCM string from on-ramp
   leftLnChgJoinString             (16), -- Left-lane-changing to join a
                                         --   platoon or CCM string
   rightLnChgJoinString            (17), -- Right-lane-changing to join a
                                         --   platoon or CCM string
   collisionAvoidLnChgOnly         (19), -- Collision avoidance by lane
                                         --   changing only
   collisionAvoidLnChgWthSpdRed    (20), -- Collision avoidance by lane
                                         --   changing and speed reduction
   collisionAvoidEmgcyStp          (21), -- Collision avoidance by emergency
                                         --   stop
   autoDecelFollowSpdProfile       (28), -- Automatic deceleration following
                                         --   designed speed profile (in
                                         --   response to speed limit change)
   stoppingClosedloopVehFollowCtl  (31), -- Stopping by closed-loop vehicle
                                         --   following control
   stoppngOpenloopDecelCmd         (32), -- Stopping by open-loop deceleration
                                         --   command
   brakeToStopManCtl               (33), -- Brake to stop in manual mode
   incGapContString                (34), -- Gradually increasing gap to longer
                                         --   desired distance but continue
                                         --   platoon or CCM control (in
                                         --   response to a fault)
   incGapRedSpdToStp               (35), -- Gradually increasing gap and
                                         --   reducing speed to stop (in
                                         --   response to a fault)
   cruiseCtl                       (36), -- Cruise control (speed regulation,
                                         --   with no forward target vehicle
                                         --   to track)
   adapCruiseCtl                   (41), -- Adaptive cruise control (vehicle
                                         --   following control without
                                         --   communication)
   coopAdapCruiseCtl               (42), -- Cooperative adaptive cruise control
                                         --   (vehicle following control using
                                         --   forward ranging sensor and
                                         --   communication data)
   manCtl                          (46), -- Manual control (including all
                                         --   maneuvers)
   coordAutoBrkForStringWthSvcBrkEngBrk (47), -- Coordinated automatic braking
                                              --   for a platoon or CCM string
                                              --   with both service brake and
                                              --   engine brake if applicable
   emgcyBrkForStringOnePlusVehWthSvcBrk (48)  -- Emergency braking for a
                                              --   platoon or CCM string: at
                                              --   least one of the vehicles
                                              --   used service brake for
                                              --   handling emergency
                                              --   situations
    } (0..255)

FrontCutIn ::= BOOLEAN
               -- True if a front cut-in is detected
               -- False if a front cut-in is not detected

END
-- Use of this module defined in SAE J2945/9
-- Latest document release for this module is Mar 2017
-- Filename: J2945-9-PersonalSafetyMessage2-2024-ph-v1.1.asn
--
-- Note: This is a *placeholder* file for the fully defined ASN.1 module.
-- Replace this file with the correct SAE file to compile a functional module.

PersonalSafetyMessage2
{joint-iso-itu-t (2) country (16) us (840) organization (1) sae (114566)
v2x-communications (1) technical-committees (1) v2x-vehicular-applications (8) technical-reports (1)
j2945 (2945) slash-9 (9) asn1-module (1) personalSafetyMessage2 (44)
version-1 (1) version-minor-1 (1)}

DEFINITIONS AUTOMATIC TAGS ::=
BEGIN

PersonalSafetyMessage2 ::= NULL

END-- Use of this module defined in SAE J2945/A
-- This standard is not released (WIP)
-- Filename: J2945-A-RGA-2024-ph-v1.1.asn
--
-- Note: This is a *placeholder* file for the fully defined ASN.1 module.
-- Replace this file with the correct SAE file to compile a functional module.
--

RoadGeometryAndAttributes
{joint-iso-itu-t (2) country (16) us (840) organization (1) sae (114566)
v2x-communications (1) technical-committees (1) v2x-core (5) technical-reports (1)
j2945 (2945) slash-a (10) asn1-module (1) roadGeometryAndAttributes (43)
version-1 (1) version-minor-1 (1)}

DEFINITIONS AUTOMATIC TAGS ::=
BEGIN

RoadGeometryAndAttributes ::= NULL

END-- Use of this module defined in SAE J2945/C
-- Latest document release for this module is Jun 2022
-- Filename: J2945-C-ProbeDataConfig-2024-rel-v1.1.asn
--

ProbeDataConfig
{joint-iso-itu-t (2) country (16) us (840) organization (1) sae (114566)
v2x-communications (1) technical-committees (1) v2x-core (5) technical-reports (1)
j2945 (2945) slash-c (12) asn1-module (1) probeDataConfig (0)
version-1 (1) version-minor-1 (1)}

DEFINITIONS AUTOMATIC TAGS ::=
BEGIN

IMPORTS
    DDate,
   DTime,
   DDateTime,
   DSRCmsgID,
   IntersectionID,
   RoadAuthorityID
      FROM Common {joint-iso-itu-t (2) country (16) us (840) organization (1) sae (114566)
      v2x-communications (1) technical-committees (1) v2x-core (5) technical-reports (1)
      j2735 (2735) part-0 (0) asn1-module (1) common (38)
      version-1 (1) version-minor-1 (1)}

    ValidRegion
      FROM TravelerInformation {joint-iso-itu-t (2) country (16) us (840) organization (1) sae (114566)
      v2x-communications (1) technical-committees (1) v2x-core (5) technical-reports (1)
      j2735 (2735) part-0 (0) asn1-module (1) travelerInformation (20)
      version-1 (1) version-minor-1 (1)};

ProbeDataConfigMessage ::= SEQUENCE (SIZE(1..255, ...)) OF ProbeDataConfig

ProbeDataConfig ::= SEQUENCE {
    descriptor          ConfigDescriptor,
    triggers            ConfigTriggers,
    maxAgeOfData        INTEGER (1..90), -- in days
    boundary            ConfigBoundary  OPTIONAL,
    ...
}

ConfigDescriptor ::= SEQUENCE {
    identifier      ConfigId,
    vehClass        CfgVehicleClass     OPTIONAL,
    roadAuthorityID RoadAuthorityID     OPTIONAL,
    percentOfResp   INTEGER (1..10)     OPTIONAL,
    -- '1' indicates report 10% of the time, '10' is 100%
    ...
}

ConfigId ::= INTEGER (1..255)

-- The following are FHWA defined vehicle classes (types)
-- See ProbeDataReport module for enumerated values
CfgVehicleClass ::= SEQUENCE    {
    motorcycles                         BOOLEAN,
    passengerCars                       BOOLEAN,
    other2axle4tireSingleUnitVehs       BOOLEAN,
    buses                               BOOLEAN,
    twoAxle6TireSingleUnitTrucks        BOOLEAN,
    threeAxleSingleUnitTrucks           BOOLEAN,
    fourOrMoreAxleSingleUnitTrucks      BOOLEAN,
    fourOrFewerAxleSingleTrailerTrucks  BOOLEAN,
    fiveAxleSingleTrailerTrucks         BOOLEAN,
    sixOrMoreAxleSingleTrailerTrucks    BOOLEAN,
    fiveOrFewerAxleMultiTrailerTrucks   BOOLEAN,
    sixAxleMultiTrailerTrucks           BOOLEAN,
    sevenOrMoreAxleMultiTrailerTrucks   BOOLEAN,
    ...
}

ConfigBoundary ::= CHOICE {
    temporalBoundary    ConfigTemporalBoundary,
    geoAndDistBoundary  ValidRegion, -- From J2735
    ...
}

-- Defines applicable periods for an event.
ConfigTemporalBoundary ::= SEQUENCE {
    beginTime           DDateTime, --From J2735
    endTime             DDateTime, --From J2735
    recurring           CfgEventRecurrence, --borrowed from J2945/4 RSM
    ...
}

-- Definition for EventRecruarance borrowed from J2945/4 RSM.
CfgEventRecurrence ::= SEQUENCE {
    startTime   DTime   OPTIONAL,  -- Time of day this period starts
    endTime     DTime   OPTIONAL,  -- Time of day this period ends
    startDate   DDate   OPTIONAL,  -- Date this period starts
    endDate     DDate   OPTIONAL,  -- Date this period ends
    -- Define days of the week for applicable periods (used by EventRecurrence)
    monday      BOOLEAN,
    tuesday     BOOLEAN,
    wednesday   BOOLEAN,
    thursday    BOOLEAN,
    friday      BOOLEAN,
    saturday    BOOLEAN,
    sunday      BOOLEAN,
    -- exclusion: TRUE: The period defined here is excluded,
    -- i.e., the period is NOT applicable to the event
    exclusion   BOOLEAN OPTIONAL,
    ...
}

ConfigTriggers ::= CHOICE {
    instantaneousTriggers   CfgInstantaneousEventTriggers,
    avgAndSumTriggers       CfgAveragedAndSummaryTriggers,
    ...
}

CfgInstantaneousEventTriggers ::= CHOICE {
    intervalEvents      CfgIntervalEvents,
    vehicleEvents       CfgVehicleEvents,
    roadwayEvents       CfgRoadwayEvents,
    commSysPerfEvents   CfgCommSysPerfEvents,
    ...
}

CfgIntervalEvents ::= SEQUENCE {
    interval        CfgInterval,
    wiperStatus     BOOLEAN                 OPTIONAL,
    vehCount        BOOLEAN                 OPTIONAL,
    -- Count of V2V equipped vehicles encountered during the interval
    weatherData     BOOLEAN                 OPTIONAL,
    transitVehData  CfgTransitVehicleData   OPTIONAL,
    -- Multiple parameters from Transit vehicles
    numOfOccupants  BOOLEAN                 OPTIONAL,
    ...
}

CfgTransitVehicleData ::= SEQUENCE {
    currNumPasngers BOOLEAN     OPTIONAL,
    avgNumPasngers  BOOLEAN     OPTIONAL,
    trnstVehSchAdh  BOOLEAN     OPTIONAL,
    ...
}

CfgInterval ::= CHOICE {
    timeInterval            INTEGER(1..36000),  -- in tenths of seconds up to an hour
    distanceInterval        INTEGER(1..100),    -- in 0.1 kilometers
    ...
}

CfgVehicleEvents ::= SEQUENCE {
    headLights              BOOLEAN                 OPTIONAL,
    fogLights               BOOLEAN                 OPTIONAL,
    hazardLights            BOOLEAN                 OPTIONAL,
    kinematicEvents         CfgKinematicEvents      OPTIONAL,
    wiperStatusChange       BOOLEAN                 OPTIONAL,
    lowSpeed                CfgLowSpeedCriteria     OPTIONAL,
    -- Speed falls below a threshold (MIN 5 KPH) for a defined duration (in seconds)
    resumedSpeed            INTEGER (1..100)        OPTIONAL,
    -- Speed goes above a certain threshold, in KPH
    vehEntrsExitsRegion     BOOLEAN                 OPTIONAL,
    -- Vehicle enters or exits the region defined in ConfigBoundary
    emerVehDetect           BOOLEAN                 OPTIONAL,
    -- Emergency vehicle detected by a non-emergency vehicle
    emerAndTransInfo        CfgEmerAndTransitInfo   OPTIONAL,
    -- Info pertaining to emergency or transit vehicles
    v2xMsgRecption          CfgMsgRecepIndicators   OPTIONAL,
    -- V2X message reception: reception of any V2X message over the communications
    -- interface(s), identified by indicating the desired data
    -- dictionary (e.g. SAE J2735, ETSI and ISO data dictionary documents) and
    -- message IDs in the configuration.
    driverAlertsAndWarnings BOOLEAN                 OPTIONAL,
    ...
}

CfgKinematicEvents ::= SEQUENCE {
    events              CfgEvents,
    hysteresis          CfgHysteresis       OPTIONAL,
    ...
}

CfgEvents ::= SEQUENCE {
    absActivated            BOOLEAN         OPTIONAL,
    tractionCtlLoss         BOOLEAN         OPTIONAL,
    stabilityCtlActivated   BOOLEAN         OPTIONAL,
    hardBraking             BOOLEAN         OPTIONAL,
    swerveThreshold         INTEGER (1..50) OPTIONAL,
    -- Lateral acceleration exceeds a certain threshold
    -- e.g. 18 represents 1.8 m/s2, 36 represents 3.6 m/s2 (units = 0.1 m/s2)
    -- Measured in meters per second squared and the threshold value of comfort
    -- is 1.8 m/s2, with medium comfort and discomfort levels of 3.6 m/s2
    -- and 5 m/s2, respectively.
    ...
}

CfgHysteresis ::= SEQUENCE {
    hysSamples      INTEGER(1..10),
    -- Value indicates the number of samples before and after the event
    hysRate         INTEGER(1..10),
    -- In 100 mSecs, value indicates sampling interval for hysteresis
    ...
}

CfgEmerAndTransitInfo ::= CHOICE {
    emerVehLightBar         BOOLEAN,
    -- Emergency vehicle light bar turned on/off (reported by the emergency vehicle only)
    reqTspEvp               BOOLEAN,
    -- TSP/EVP requested (transit and emergency vehicles only)
    transitVehPassCnt       BOOLEAN,
    -- Transit Vehicle passenger count change and resulting number of occupants
    transitVehDoor          BOOLEAN,
    -- Transit vehicle door opened and number of passengers entering / exiting
    ...
}

CfgMsgRecepIndicators ::= SEQUENCE {
    msgDictionary   CfgMsgDictionary                    OPTIONAL,
    messages SEQUENCE (SIZE(1..8, ...)) OF DSRCmsgID    OPTIONAL,
    --DSRCmsgID imported from DSRC
    ...
}

-- Indicate which dictionary type
CfgMsgDictionary ::= ENUMERATED {
    sae     (1),
    etsi    (2),
    iso     (3),
    ...
}

-- The following are criteria by which the associated event will be reported
CfgRoadwayEvents ::= SEQUENCE {
    obstacleDetected        BOOLEAN,
    adverseRoadSurface      BOOLEAN,
    -- Adverse road surface condition (non-weather related: potholes, road roughness).
    trafficSigEncounters    CfgTrafficSigEncounters OPTIONAL,
    -- Traffic signal related parameters
    trfsigLightOut          BOOLEAN,
    trfsigRoadGeoMismatch   BOOLEAN,
    roadSignInfo            CfgRoadSignInfo         OPTIONAL,
    lowLaneMarkReflect      INTEGER (1..100)        OPTIONAL,
    -- Identify types of roadsigns and report back reflectivity
    -- Low lane marking retro reflectivity (falls below a specified threshold
    -- in % light returned)
    roadsignIncnstncy       BOOLEAN,
    -- Roadsign inconsistency or unexpected closure (posted sign inconsistent
    -- with on-board map)
    laneGeoIncnstncy        BOOLEAN,
    -- Lane geometry inconsistency (difficult to interpret because of being covered
    -- up or ambiguous, or different from on-board map)
    incidentDetect          BOOLEAN,
    -- Incident detection (car accident, wrong way driver, slowdown in
    -- opposite direction)
    workZoneCharDetect      BOOLEAN,
    -- Detection of work zone characteristics: workers present, lane shifts and
    -- lane closures
    inclWeatherDetect       BOOLEAN,
    -- Detection of inclement weather or weather-related road surface
    -- condition (SAE J2945/3 - heavy rain, fog, wind, ice, snow)
    railrdCrossActivated    BOOLEAN,
    -- Railroad crossing activated
    drawBridgeActivated     BOOLEAN,
    -- Draw bridge activated
    ...
}

CfgTrafficSigEncounters ::= SEQUENCE {
    intersections           SEQUENCE (SIZE(1..100)) OF IntersectionID   OPTIONAL,
    -- Intersection IDs typically used in SPAT and MAP messsages
    trfcsigApproachDelay    INTEGER (1..3600)   OPTIONAL,
    -- In seconds, triggered if higher
    trfsigApproachSpeed     INTEGER (1..200)    OPTIONAL,
    -- In KPH, triggered if lower
    trfsigArrivalGreen      BOOLEAN             OPTIONAL,
    trfsigArrivalRed        BOOLEAN             OPTIONAL,
    trfsigPedDelay          INTEGER (1..300)    OPTIONAL,
    -- In seconds, triggered if higher
    trfsigSpatMismatch      BOOLEAN             OPTIONAL,
    trfsigSpatTimingError   BOOLEAN             OPTIONAL,
    ...
}

CfgRoadSignInfo ::= SEQUENCE {
        roadsignDetection       CfgRoadSignTypes,
        -- Road sign types
        lowRoadsignReflect1     INTEGER (1..250)    OPTIONAL,
        -- Min threshold for 1st color
        lowRoadsignReflect2     INTEGER (1..250)    OPTIONAL,
        -- Min threshold for 2nd color

        -- Low roadsign retroreflectivity (in cd/lx/m2 falls below a specified threshold)
        -- Reflectivity threshold is dependent on the type of roadsign
        -- Reference: U.S.DOT, FHWA, Manual on Uniform Traffic Control Devices for
        -- Streets and Highways, 2009 Edition
    ...
}

CfgRoadSignTypes ::= SEQUENCE {
    whiteOnGreen    BOOLEAN     OPTIONAL,
    blackOnYellow   BOOLEAN     OPTIONAL,
    blackOnOrange   BOOLEAN     OPTIONAL,
    whiteOnRed      BOOLEAN     OPTIONAL,
    blackOnWhite    BOOLEAN     OPTIONAL,
    octagon         BOOLEAN     OPTIONAL,
    eqlatTriangle   BOOLEAN     OPTIONAL,
    circle          BOOLEAN     OPTIONAL,
    pennant         BOOLEAN     OPTIONAL,
    pentagon        BOOLEAN     OPTIONAL,
    crossbuck       BOOLEAN     OPTIONAL,
    diamond         BOOLEAN     OPTIONAL,
    trapezoid       BOOLEAN     OPTIONAL,
    other           BOOLEAN     OPTIONAL,
    -- Reference: U.S.DOT, FHWA, Manual on Uniform Traffic Control Devices for
    -- Streets and Highways, 2009 Edition
    ...
}


CfgCommSysPerfEvents ::= SEQUENCE {
    j2945-1ChanBusyThresh   INTEGER (1..100)    OPTIONAL,
    -- Based on J2945/1 Channel busy percentage measured over last 100ms
    rfDataRsuInfo           BOOLEAN             OPTIONAL,
    numRsusObservedThresh   INTEGER (1..254)    OPTIONAL,
    -- Threshold for numOfRsusObserved

    -- RF Triggers:
    rfV2xJamDetectThresh    INTEGER (1..140)    OPTIONAL,
    -- 5.9 GHZ V2X Radio Jamming detection (if equipped)in -dBm
    j2945-1VehDensThresh    INTEGER (1..255)    OPTIONAL,
    -- J2945/1 Vehicle Density in range exceeds specified threshold (number of vehicles)
    j2945-1CqiBelowThresh   INTEGER (1..100)    OPTIONAL,
    -- J2945/1 CQI falls below a specified threshold (poor link quality)
    j2945-1TrackErrorThresh INTEGER (1..100)    OPTIONAL,
    -- J2945/1 Tracking Error estimate exceed a specified threshold in meters.

    -- GNSS Performance Triggers:
    gnssHdopExceedsThresh   INTEGER (1..20)     OPTIONAL,
    -- HDOP exceeds a specified threshold
    -- If stationary do not report more than once
    gnssSatsBelowThresh     INTEGER (1..20)     OPTIONAL,
    -- Satellites in view goes below a specified threshold
    gnssJammingDetect       BOOLEAN             OPTIONAL,
    -- Jamming detected
    ...
}

CfgAveragedAndSummaryTriggers ::= CHOICE {
    averagedTriggers        CfgAveragedTriggers,
    summaryTriggers         CfgSummaryTriggers,
    ...
}

CfgAveragedTriggers ::= SEQUENCE {
    avgSpeed            BOOLEAN OPTIONAL, -- in KPH
    avgStopDuration     BOOLEAN OPTIONAL, -- in Seconds
    avgFuelConsumption  BOOLEAN OPTIONAL, -- in Liters
    avgEmissions        BOOLEAN OPTIONAL,
    avgNumOfOccupants   BOOLEAN OPTIONAL,
    ...
}

CfgSummaryTriggers ::= SEQUENCE {
    regTravelTime           BOOLEAN                 OPTIONAL,
    -- Total travel time to traverse the region in seconds
    regVehDistTraveled      BOOLEAN                 OPTIONAL,
    -- Total vehicle distance traveled within the region (kilometers)
    regVehTimeTraveled      BOOLEAN                 OPTIONAL,
    -- Total vehicle time traveled within the region (seconds)
    fuelConsumption         BOOLEAN                 OPTIONAL,
    -- Total fuel consumption in liters
    totalVehEmissions       BOOLEAN                 OPTIONAL,
    -- Total vehicle emissions
    numOfLowSpeedEvents     CfgLowSpeedCriteria     OPTIONAL, -- Low speed threshold
    -- Number of times speed dropped below a low speed threshold (low speed threshold
    -- must be greater than 5 Km/h)
    timeStopped             CfgStoppedCriteria      OPTIONAL, -- Stopped speed threshold
    -- Seconds spent at speed less than the specified stopped threshold
    numOfStopped            CfgStoppedCriteria      OPTIONAL,
    -- Number of times the speed fell below the specified stopped threshold
    locOfStops              BOOLEAN                 OPTIONAL,
    -- Each location and duration in seconds where the speed drops below the
    -- specified stopped threshold
    regNumOfVehPassed       BOOLEAN                 OPTIONAL,
    -- Number of vehicles passed over the configuration region
    regNumOfSurpassedVeh    BOOLEAN                 OPTIONAL,
    -- Number of vehicles that passed the recording vehicle over the configuration region
    totalMsgsReceived       CfgMsgRecepIndicators   OPTIONAL,
    -- Total messages received by the message type indicated in the configuration
    ...
}

CfgLowSpeedCriteria ::= SEQUENCE {
    lowSpeedThreshold   INTEGER (5..100),               -- In KPH
    lowSpeedTimeThresh  INTEGER (1..30)     OPTIONAL,   -- In seconds
    ...
}

CfgStoppedCriteria ::= SEQUENCE {
    stoppedSpeedThreshold   INTEGER (1..30),    -- in KPH
    amountOfTimeBelow       INTEGER (1..300),   -- in seconds
    ...
}


END-- Use of this module defined in SAE J2945/C
-- Latest document release for this module is Jun 2022
-- Filename: J2945-C-ProbeDataReport-2024-rel-v1.1.asn
--
ProbeDataReport
{joint-iso-itu-t (2) country (16) us (840) organization (1) sae (114566)
v2x-communications (1) technical-committees (1) v2x-core (5) technical-reports (1)
j2945 (2945) slash-c (12) asn1-module (1) probeDataReport (1)
version-1 (1) version-minor-1 (1)}

DEFINITIONS AUTOMATIC TAGS ::=
BEGIN

IMPORTS
    DTime,
   DDateTime,
   IntersectionID,
   Speed,
   Heading,
   MeanVariation,
   PositionalAccuracy,
   Position3D,
    RoadAuthorityID,
   VehicleSize,
   VehicleMass
      FROM Common {joint-iso-itu-t (2) country (16) us (840) organization (1) sae (114566)
      v2x-communications (1) technical-committees (1) v2x-core (5) technical-reports (1)
      j2735 (2735) part-0 (0) asn1-module (1) common (38)
      version-1 (1) version-minor-1 (1)}

    NtcipEssData
      FROM RoadWeatherMessage {joint-iso-itu-t (2) country (16) us (840) organization (1) sae (114566)
      v2x-communications (1) technical-committees (1) v2x-core (5) technical-reports (1)
      j2945 (2945) slash-3 (3) asn1-module (1) roadWeatherMessage (0)
      version-2 (2) version-minor-1 (1)}

    ConfigId
      FROM ProbeDataConfig {joint-iso-itu-t (2) country (16) us (840) organization (1) sae (114566)
      v2x-communications (1) technical-committees (1) v2x-core (5) technical-reports (1)
      j2945 (2945) slash-c (12) asn1-module (1) probeDataConfig (0)
      version-1 (1) version-minor-1 (1)};

ProbeDataReportMessage ::= SEQUENCE {
    configId            ConfigId,
    reportChar          ReportCharacteristics,
    roadAuthorityID     RoadAuthorityID             OPTIONAL,
    instantaneousRecs   RptInstantaneousRecords     OPTIONAL,
    avgAndSumRec        RptAveragedAndSummaryRecord OPTIONAL,
    ...
} (WITH COMPONENTS {..., instantaneousRecs PRESENT} |
   WITH COMPONENTS {..., avgAndSumRec PRESENT})

ReportCharacteristics ::= SEQUENCE {
    -- The next four data elements are mandatory in every report record
    timeStamp           DDateTime,
    position            Position3D,
    posAccuracy         PositionalAccuracy,
    velocity            RptVelocity,
    vehicleClass        RptVehicleClass     OPTIONAL, -- FHWA classes
    devType             RptDevType          OPTIONAL, -- OBU Type
    vehicleSize         VehicleSize         OPTIONAL,
    vehicleMass         VehicleMass         OPTIONAL,
    vehPassengerCount   INTEGER (1..255)    OPTIONAL,
    ...
}

-- The following are FHWA defined vehicle classes (types)
RptVehicleClass ::= ENUMERATED  {
    motorcycles                         (1),
    passengerCars                       (2),
    other2axle4tireSingleUnitVehs       (3),
    buses                               (4),
    twoAxle6TireSingleUnitTrucks        (5),
    threeAxleSingleUnitTrucks           (6),
    fourOrMoreAxleSingleUnitTrucks      (7),
    fourOrFewerAxleSingleTrailerTrucks  (8),
    fiveAxleSingleTrailerTrucks         (9),
    sixOrMoreAxleSingleTrailerTrucks    (10),
    fiveOrFewerAxleMultiTrailerTrucks   (11),
    sixAxleMultiTrailerTrucks           (12),
    sevenOrMoreAxleMultiTrailerTrucks   (13),
    ...
}

-- Device Types (OBU type)
RptDevType ::= SEQUENCE {
    oemOrAftermarket    BOOLEAN,
    canOrIvnConnected   BOOLEAN,
    mcoCapable          BOOLEAN OPTIONAL,
    ...
}

RptInstantaneousRecords ::= SEQUENCE (SIZE(1..255, ...)) OF RptInstantaneousRecord

RptInstantaneousRecord ::= SEQUENCE {
    timeOfInstantRec    DDateTime,
    locOfInstantRec     Position3D,
    accOfPosition       PositionalAccuracy,
    velOfInstantRec     RptVelocity,
    record              RptInstantaneousRecordData  OPTIONAL,
    ...
}

-- Heading and Speed imported from J2735
RptVelocity ::= SEQUENCE {
    speed       Speed,            -- in km/hr
    speedStdDev StdDev  OPTIONAL, -- in km/hr
    heading     Heading OPTIONAL,
    ...
}

RptInstantaneousRecordData ::= CHOICE {
    intervalEvents      RptIntervalEvents,
    vehEvents           RptVehicleEvents,
    roadwayEvents       RptRoadwayEvents,
    commSysPerfEvents   RptCommSysPerfEvents,
    ...
}

RptAveragedAndSummaryRecord ::= SEQUENCE {
    startTime       DDateTime,  --Time at the start of data capture
    startLoc        Position3D, --Position at startTime
    startAccOfPos   PositionalAccuracy, --Accuracy of starting position
    endTime         DDateTime,  --Time at the end of data capture
    endLoc          Position3D, --Position at endTime
    endAccOfPos     PositionalAccuracy, --Accuracy of ending position
    record          RptAvgAndSummaryRecordData,
    ...
}

RptAvgAndSummaryRecordData ::= CHOICE {
    averagedRecord      RptAveragedRecord,
    summaryRecord       RptSummaryRecord,
    ...
}

RptIntervalEvents   ::= SEQUENCE {
    wiperStatus     RptWiperStatus      OPTIONAL,
    vehCount        INTEGER (0..10000)  OPTIONAL,
    -- Number of V2V-equipped vehicles encountered
    weatherData     RptVehicleReport    OPTIONAL,
    transitVehData  RptTransitVehData   OPTIONAL,
    numOfOccupants  INTEGER (0..255)    OPTIONAL,
    -- 254 indicates > 253, 255 is reserved
    ...
}

RptVehicleReport ::= SEQUENCE (SIZE(1..32)) OF NtcipEssData
-- NtcipEssData is defined in RWM (J2945/3)

RptTransitVehData ::= SEQUENCE {
    currNumPasngers INTEGER (0..255)    OPTIONAL,
    avgNumPasngers  INTEGER (0..255)    OPTIONAL,
    trnstVehSchAdh  INTEGER (-200..55)  OPTIONAL,
    -- Neg nums indicates running behind,
    -- positive indicates running ahead of schedule, in minutes
    ...
}


-- For each below, set to TRUE if the correpsonding event occured (triggered)
RptVehicleEvents ::= CHOICE {
    headLights          NULL,
    fogLights           NULL,
    hazardLights        NULL,
    kinematicEvents     RptKinematicEvents,
    wiperStatusChange   NULL,
    lowSpeed            NULL,
    resumedSpeed        NULL,
    vehEntrsExitsRegion NULL,
    emerVehDetect       NULL,
    emerVehLightBar     NULL,
    reqTspEvp           NULL,
    transitVehPassCnt   NULL,
    transitVehDoor      NULL,
    v2xMsgRecption      NULL,
    -- Indicates reception of the V2X message identified in the configuration.
    driverAlertsAndWarnings     RptDriverAlertsAndWarnings,
    ...
}

RptDriverAlertsAndWarnings ::= CHOICE {
    j2945Slash1Eebl         NULL,
    -- Emergency Electronic Brake Lights
    j2945Slash1Fcw          NULL,
    -- Forward Crash Warning
    j2945Slash1BswLcw       NULL,
    -- Blind Spot Warning/Lane Change Warning
    j2945Slash1Ima          NULL,
    -- Intersection Movement Assist
    j2945Slash1Lta          NULL,
    -- Left Turn Assist
    j2945Slash1Clw          NULL,
    -- Control Loss Warning
    redLightViolationWarn   NULL,
    emerVehAlert            NULL,
    otherAlert              NULL,
    otherWarning            NULL,
    ...
}

RptKinematicEvents ::= SEQUENCE {
    events              RptEvents,
    hysteresis          RptHysteresisRecord OPTIONAL,
    ...
}

RptEvents ::= CHOICE {
    absActive           BOOLEAN,
    tractionCtlLoss     BOOLEAN,
    stabilityCtlActive  BOOLEAN,
    hardBraking         BOOLEAN, -- Defined in J2945/1
    swerve              BOOLEAN,
    ...
}

RptHysteresisRecord ::= SEQUENCE (SIZE(1..20)) OF RptHysteresis

RptHysteresis ::= SEQUENCE {
    time                DTime,
    position            Position3D,
    positionalAccuracy  PositionalAccuracy  OPTIONAL,
    velocity            RptVelocity,
    ...
}

RptRoadwayEvents ::= CHOICE {
    obstacleDetected        NULL,
    adverseRoadSurface      RptRoadRoughness,
    trfsigEncounters        RptTrafficSigEncounters,
    trfsigLightOut          NULL,
    trfsigRoadGeoMismatch   NULL,
    roadsignDetection       NULL,
    lowRoadsignReflect      NULL,
    lowLaneMarkReflect      NULL,
    roadsignIncnstncy       NULL,
    laneGeoIncnstncy        NULL,
    incidentDetect          NULL,
    workZoneCharDetect      NULL,
    inclWeatherDetect       NULL,
    railrdCrossActiv        NULL,
    drawBridgeActiv         NULL,
    ...
}

RptRoadRoughness ::= SEQUENCE {
    meanVerticalVariation       MeanVariation,
    verticalVariationStdDev     StdDev          OPTIONAL,
    -- Standard deviation in microns
    meanHorizontalVariation     MeanVariation   OPTIONAL,
    horizontalVariationStdDev   StdDev          OPTIONAL,
    -- Standard deviation in microns
    ...
}

StdDev ::= INTEGER (0..10000)


RptTrafficSigEncounters ::= SEQUENCE {
    intersectionID          IntersectionID  OPTIONAL, -- Imported from J2735
    -- Received by OBU in SPAT and MAP messages
    trafficMetrics          RptTrafficMetrics,
    ...
}

RptTrafficMetrics ::= CHOICE {
    trfsigApproachDelay     NULL,
    trfsigApproachSpeed     NULL,
    trfsigArrivalGreen      NULL,
    trfsigArrivalRed        NULL,
    trfsigPedDelay          NULL,
    trfsigSpatMismatch      NULL,
    trfsigSpatTimingError   NULL,
    ...
}

RptCommSysPerfEvents ::= CHOICE {
    j2945-1ChanBusy         NULL,
    rfDataRsuInfo           OCTET STRING (SIZE(6)),
    -- Report Source MAC / Layer 2 Source ID of any RSUs that we see/hear
    numOfRsusObserved       INTEGER (1..255),
    -- Count of encountered RSUs if count higher than threshold
    rfV2xJamDetect          NULL,
    j2945-1VehDens          NULL,
    j2945-1CqiBelow         NULL,
    j2945-1TrackingError    NULL,
    gnssHdopExceeds         NULL,
    gnssErrElipse           NULL,
    gnssSatsBelow           NULL,
    jammingDetect           NULL,
    ...
}

RptWiperStatus ::= ENUMERATED {off, low, medium, high, ...}

RptAveragedRecord ::= SEQUENCE {
    avgSpeed            Speed               OPTIONAL,
    -- in km/hr
    speedStdDev         StdDev              OPTIONAL,
    -- in km/hr
    avgStopDuration     INTEGER (1..36000)  OPTIONAL,
    -- in tenths of seconds up to an hour
    avgStopStdDev       StdDev              OPTIONAL,
    -- in tenths of seconds
    avgFuelConsumption  INTEGER (1..255)    OPTIONAL,
    avgEmissions        RptEmissions        OPTIONAL,
    avgNumOfOccupants   INTEGER (1..255)    OPTIONAL,
    ...
}

RptSummaryRecord ::= SEQUENCE {
    regTravelTime           INTEGER (1..3600)   OPTIONAL,
    -- Total travel time to traverse the region in seconds
    regVehDistTraveled      INTEGER (1..500)    OPTIONAL,
    -- Total vehicle distance traveled in kilometers
    regVehTimeTraveled      INTEGER (1..3600)   OPTIONAL,
    -- Total vehicle time traveled within the region (seconds)
    fuelConsumption         INTEGER (1..255)    OPTIONAL,
    -- Total fuel consumption in liters
    totalVehEmissions       RptEmissions        OPTIONAL,
    -- Total vehicle emissions
    numOfLowSpeedEvents     INTEGER (1..255)    OPTIONAL, -- Low speed threshold
    -- Number of times speed dropped below a low speed threshold
    timeStopped             INTEGER (1..36000)  OPTIONAL,
    -- Total Stopped time in tenths of seconds up to an hour
    numOfStopped            INTEGER (1..255)    OPTIONAL,
    -- Number of times the speed fell below the specified stopped threshold
    locOfStops              RptLocOfStops       OPTIONAL,
    -- Each location and duration in seconds where the speed drops below
    -- the specified stopped threshold
    regNumOfVehPassed       INTEGER (1..255)    OPTIONAL,
    -- Number of vehicles passed over the configuration region
    regNumOfSurpassedVeh    INTEGER (1..255)    OPTIONAL,
    -- Number of vehicles that passed the recording vehicle over the configuration region
    totalMsgsReceived       INTEGER (1..255)    OPTIONAL,
    -- Total messages received by the message type indicated in the configuration
    ...
}

RptEmissions ::= SEQUENCE {
    hydrocarbons    INTEGER (1..1000) OPTIONAL, -- in parts per million
    co              INTEGER (1..1000) OPTIONAL, -- in parts per million
    co2             INTEGER (1..1000) OPTIONAL, -- in parts per billion
    no              INTEGER (1..1000) OPTIONAL, -- in parts per million
    no2             INTEGER (1..1000) OPTIONAL, -- in parts per billion
    so2             INTEGER (1..1000) OPTIONAL, -- in parts per billion
    o3              INTEGER (1..1000) OPTIONAL, -- in parts per 100 billion
    -- Particulates of 10 micrometers or less in diameter
    pm10            INTEGER (1..1000) OPTIONAL, -- in micrograms per cubic meter
    -- Particulates of 2.5 micrometers or less in diameter
    pm25            INTEGER (1..1000) OPTIONAL, -- in micrograms per cubic meter
    ...
}

RptLocOfStops ::= SEQUENCE {
    locationOfStop      Position3D,
    locAccOfStop        PositionalAccuracy, -- Imported from J2735
    durationOfStop      INTEGER (1..36000), -- in tenths of seconds up to an hour
    ...
}

END

 -- Use of this module defined in SAE J3186
-- Latest document release for this module is Mar 2023
-- Filename: J3186-ManeuverSharingandCoordinatingMessage-2024-rel-v1.1.asn
--

ManeuverSharingAndCoordinatingMessage
{joint-iso-itu-t (2) country (16) us (840) organization (1) sae (114566)
v2x-communications (1) technical-committees (1) v2x-vehicular-applications (8)
technical-reports (1) j3186 (3186) asn1-module (1) maneuverSharingAndCoordinatingMessage (42)
version-1 (1) version-minor-1 (1)}

DEFINITIONS AUTOMATIC TAGS ::=
BEGIN

IMPORTS
    AccelerationSet4Way,
    DDateTime,
    Heading,
    Position3D,
    PositionalAccuracy,
    PositionConfidenceSet,
    Speed,
    TemporaryID,
    VehicleSize
        FROM Common {joint-iso-itu-t (2) country (16) us (840) organization (1) sae (114566)
      v2x-communications (1) technical-committees (1) v2x-core (5) technical-reports (1)
      j2735 (2735) part-0 (0) asn1-module (1) common (38)
      version-1 (1)  version-minor-1 (1)};

ManeuverSharingAndCoordinatingMessage ::= SEQUENCE {
    mSCMTimestamp               DDateTime,
    hVPos                       Position3D             OPTIONAL,
    hVPosXYConf                 PositionalAccuracy     OPTIONAL,
    -- HV's reference position and accuracy
    -- Required for mSCMType = 0, 1, 3, and 6
    -- Not allowed otherwise
    mSCMType                    MSCMType,
    sourceID                    TemporaryID,
    destinationIDs              TemporaryIDList        OPTIONAL,
    -- RVs' IDs
    -- Required for mSCMType = 1, 2, 3, 4, 5, 6 and 7
    -- Allowed for mSCMType = 0
    maneuverID                  MSMManeuverID             OPTIONAL,
    -- MSCS session ID by being combined with HV's ID
    -- Required for mSCMType = 1, 2, 3, 4, 5, 6 and 7
    -- Not allowed for mSCMType = 0
    maneuver                    Maneuver               OPTIONAL,
    -- Required for mSCMType = 0, 1 and 6
    -- Allowed for mSCMType = 2 in order to propose adjustments
    -- Not allowed for mSCMType = 3, 4, 5 and 7
    responseFlag                ResponseFlag           OPTIONAL,
    -- Indication of acceptance or rejection
    -- Required for mSCMType = 2
    -- Not allowed otherwise
    reasonCode                 ReasonCode              OPTIONAL,
    -- Allowed for mSCMType = 2, 4 and 5
    -- Not allowed otherwise
    maneuverExecutionStatus    ManeuverExecutionStatus OPTIONAL,
    -- Required for mSCMType = 7
    -- Not allowed otherwise
    ...
}

MSCMType ::= ENUMERATED {
    maneuverIntent                (0),
    maneuverRequest               (1),
    maneuverResponse              (2),
    maneuverReservation           (3),
    hVManeuverCancellation        (4),
    rVManeuverCancellationRequest (5),
    emergencyManeuverReservation  (6),
    maneuverExecutionStatus       (7),
    ...
}

TemporaryIDList ::= SEQUENCE (SIZE(1..32)) OF TemporaryID

MSMManeuverID ::= INTEGER (0..255)

Maneuver ::= SEQUENCE {
    subManeuverList SubManeuverList,
    ...
}

SubManeuverList ::= SEQUENCE (SIZE(1..32)) OF SubManeuver

SubManeuver ::= SEQUENCE {
    executantVehID      TemporaryID,
    affectedVehIDs      TemporaryIDPointer,
    currentStateData    CurrentStateData,
    targetRoadResource  TargetRoadResource OPTIONAL,
    startTime           DDateTime,                   -- Temporal characteristics
    endTime             DDateTime,
    minSpeed            Speed              OPTIONAL, -- Kinematic characteristics
    maxSpeed            Speed              OPTIONAL,
    ...
}

TemporaryIDPointer ::= BIT STRING (SIZE(1..32))
-- The size shall be identical to the size of destinationIDs.

CurrentStateData ::= SEQUENCE {
    executantVehPos           MSCMPositionOffsetXYZ     OPTIONAL,
    executantVehPosConfidence PositionConfidenceSet OPTIONAL,
    speed                     Speed,
    heading                   Heading,
    accel4way                 AccelerationSet4Way   OPTIONAL,
    size                      VehicleSize,
    ...
}

MSCMPositionOffsetXYZ ::= SEQUENCE {
    offsetX     MSCMObjectDistance,
    offsetY     MSCMObjectDistance,
    offsetZ     MSCMObjectDistance OPTIONAL
}

MSCMObjectDistance ::= INTEGER(-32767..32767) -- LSB units of 0.1 meters

TargetRoadResource ::= SEQUENCE {
    tRRType         TRRType,
    tRRLocation     TRRLocation,
    ...
}

TRRType ::= ENUMERATED {
    tRRType1 (0),
    tRRType2 (1),
    tRRType3 (2),
    ...
}

TRRLocation ::= CHOICE {
    tRRLocationType1 TRRLocationType1,
    -- This shall be chosen when tRRType = 0 (tRRType1)
    tRRLocationType2 TRRLocationType2,
    -- This shall be chosen when tRRType = 1 (tRRType2)
    tRRLocationType3 TRRLocationType3,
    -- This shall be chosen when tRRType = 2 (tRRType3)
    ...
}

TRRLocationType1 ::= SEQUENCE {
    tRRLength         TRRLength,
    frontSidePosition MSCMPositionOffsetXYZ,
    laneOffset        LaneOffset,
    tRRMovement       Speed OPTIONAL,
    ...
}

TRRLocationType2 ::= SEQUENCE {
    safetyGap        TRRLength,
    frontSideVehicle SurroundingVehicleInfo OPTIONAL,
    rearSideVehicle  SurroundingVehicleInfo OPTIONAL,
    tRRLength        TRRLength              OPTIONAL,
    laneOffset       LaneOffset,
    ...
}

TRRLocationType3 ::= SEQUENCE OF MSCMPositionOffsetXYZ

TRRLength ::= INTEGER (0..4095)  -- LSB units are 0.1 meters

LaneOffset ::= ENUMERATED {
    currentLane     (0),
    firstLeftLane   (1),
    firstRightLane  (2),
    secondLeftLane  (3),
    secondRightLane (4),
    thirdLeftLane   (5),
    thirdRightLane  (6),
    ...
}

SurroundingVehicleInfo ::= SEQUENCE {
    surroundingVehicleID       TemporaryID,
    surroundingVehiclePosition MSCMPositionOffsetXYZ,
    surroundingVehicleSize     VehicleSize,
    ...
}

ResponseFlag ::= BOOLEAN

ReasonCode ::= ENUMERATED {
    unknown                             (0),
    unableToConform                     (1),
    unwanted                            (2),
    unableToUnderstand                  (3),
    erroneousBehaviorDetected           (4),
    misbehaviorAttackDetected           (5),
    rVManeuverCancellationRequestIssued (6),
    sessionIDConflicted                 (7),
    ...
}

ManeuverExecutionStatus ::= ENUMERATED {
    started         (0),
    inProgress      (1),
    completed       (2),        -- successfully finished
    terminated      (3),        -- unsuccessfully finished
    ...
}

END

-- Filename: ISO17573-EfcDataDictionary.asn
--

EfcDataDictionary
{iso(1) standard(0) 17573 dd(3) version1(1)}

DEFINITIONS AUTOMATIC TAGS ::=
BEGIN

EXPORTS ALL;

-- useful subtypes (with no semantics associated)

Int1Unsigned ::= INTEGER (0..255)

Int1Signed ::= INTEGER (-128..127)

Int2Unsigned ::= INTEGER (0..65535)

Int2Signed ::= INTEGER (-32768..32767)

Int3Unsigned ::= INTEGER (0..16777215)

Int4Unsigned ::= INTEGER (0..4294967295)

Int4Signed ::= INTEGER (-2147483648..2147483647)

Int8Unsigned ::= INTEGER (0..9223372036854775807) -- 0 to 2^63-1,

Int8Signed ::= INTEGER (-9223372036854775808..9223372036854775807) -- -2^63 to 2^63-1,

-- 5.2   Subtypes of simple data types

AccountStatus ::= INTEGER {
  ok        (0),
  low       (1),
  empty     (2),
  negative  (3)
  -- (4-127) are reserved for future CEN use
  -- (128-255) are reserved for private use
}(0..255)

ActualNumberOfPassengers ::= Int1Unsigned

EcfAltitude ::= Int2Signed

CO2EmissionValue ::= Int2Unsigned

ContractAuthenticator ::= OCTET STRING

ContractSerialNumber ::= Int4Unsigned

CopValue ::= INTEGER {
  noEntry              (0),
  co2class1        (1),
  co2class2        (2),
  co2class3        (3),
  co2class4        (4),
  co2class5        (5),
  co2class6        (6),
  co2class7        (7)
  -- (8-15) are reserved for future CEN use
} (0..15)

CountryCode ::= BIT STRING(SIZE(10))

DescriptiveCharacteristics ::= INTEGER {
  noEntry (0)
  -- (1..50) are reserved for future CEN use
  -- (51..255) are reserved for private use
} (0..255)

DetectionMode ::= INTEGER {
  measured     (0),
  inferred     (1),
  lac          (2)
  -- (3-127) are reserved for future CEN use
  -- (128-255) are reserved for private use
}(0..255)


EmissionUnit ::= INTEGER {
  mgPerKm   (0),
  mgPerKwh  (1)
} (0..1)

EngineCharacteristics ::= INTEGER {
  noEntry                                     (0),
  noEngine                                    (1),
  petrolUnleaded                              (2),
  petrolLeaded                                (3),
  diesel                                      (4),
  lpg                                         (5),
  battery                                     (6),
  solar                                       (7),
  hybrid                                      (8),
  hydrogen                                    (9),
  multiFuel                                   (10),
  bivalentPetrolLpg                           (11),
  bivalentPetrolCng                           (12),
  combinedPetrolElectric                      (13),
  cng                                         (14),
  lng                                       (15),
  combinedDieselElectric                      (16),
  combinedHydrogenElectric                    (17),
  bivalentHydrogenPetrol                      (18),
  bivalentHydrogenPetrolElectricEngine        (19),
  fuelCellHydrogen                            (20),
  fuelCellPetrol                              (21),
  fuelCellMethanol                            (22),
  fuelCellEthanol                             (23),
  fuelCellDiesel                              (24),
  combinedMultiFuelElectricEngine             (25),
  combinedCngElectricEngine                   (26),
  combinedLngElectricEngine                   (27),
  petrolEthanol                               (28),
  combinedLpgElectricEngine                   (29),
  hybridPetrolExternalBattery               (30),
  hybridDieselExternalBattery               (31),
  hybridLpgExternalBattery                    (32),
  hybridHydrogenExternalBattery               (33),
  hybridMultiFuelExternalBattery              (34),
  hybridCngExternalBattery                    (35),
  hybridLngExternalBattery                    (36),
  hybridBivalentHydrogenPetrolExternalBattery (37),
  hydrogenCng                                 (38),
  hydrogenLng                                (39),
  hybridHydrogenCngExternalBattery            (40),
  hybridHydrogenLngExternalBattery            (41),
  ethanol                                     (42),
  hybridFuelCellHydrogen                      (43),
  hybridFuelCellHydrogenExternalBattery       (44),
  dualFuelLngDiesel                           (45),
  electricExternal                            (46),
  biogas                                      (47),
  bioDiesel                                   (48),
  bioPetrol                                   (49),
  bivalentPetrolBiogas                        (50),
  combinedBiogasElectricEngine                (51),
  dualFuelCngDiesel                           (52),
  -- (53-254) are reserved for future CEN and ISO use
   other                                      (255)
} (0..255)


EquipmentIccId ::= OCTET STRING

EquipmentObuId ::= OCTET STRING

EquipmentStatus ::= BIT STRING (SIZE(16))

EuroValue ::= INTEGER {
  noEntry  (0),
  euro1     (1),
  euro2     (2),
  euro3     (3),
  euro4     (4),
  euro5     (5),
  euro6     (6),
  euro7     (7), -- reserved for the upcoming Euro Emission Category 7
  -- (8-14) are reserved for future CEN use
  eev    (15)
}(0..15)

FutureCharacteristics ::= INTEGER {
  noEntry       (0),
  airSuspension   (1)
  -- (2..255) are reserved for future CEN use
} (0..255)

IssuerIdentifier::= INTEGER(0 .. 16383)

EcfLatitude ::= Int4Signed

DistanceUnit ::= INTEGER {
  kilometres    (0),
  miles          (1), -- deprecated value kept for legacy reasons
  metres        (2),
  yards         (3), -- deprecated value kept for legacy reasons
  feet          (4), -- deprecated value kept for legacy reasons
  decimetres    (5),
  quartermetres   (6), -- deprecated value kept for legacy reasons
  centimeters   (7),
  millimeters   (8)
  -- (9-127) are reserved for future CEN use
  -- (128-255) are reserved for private use
} (0..255)

LocalVehicleClassId ::= Int2Unsigned

LocationClassId ::= Int4Unsigned

EcfLongitude ::= Int4Signed

PaymentSecurityData ::= OCTET STRING

PayUnit ::= OCTET STRING (SIZE(2))
-- Value Assignments:
-- where xxx is the BCD representation of "Currency" as defined in ISO 4217
-- '0xxx'H Currency in main units
-- '1xxx'H Currency in minor units of 10 :1 ('dime')
-- '2xxx'H Currency in minor units of 100 :1 ('cents')
-- '3xxx'H Currency in minor units of 1000 :1
-- '4xxx'H Currency in 'major' units / 10 (e.g. 10 Euro)
-- '5xxx'H Currency in 'major' units / 100 (e.g. 100 US Dollars)
-- '6xxx'H Currency in 'major' units / 1000
-- '7xxx'H Currency in 'major' units / 10000
-- '8xxx'H Currency in 'major' units / 100000
-- 'Bxxx'H Currency in minor units of 10000 :1
-- 'Cxxx'H Currency in minor units of 100000 :1
-- 'Dxxx'H Currency in minor units of 1000000 :1
-- '9xxx'H Tokens where xxx is Purse Provider specific coding.
-- 'Axxx'H Charging Unit Codes denoting quantification of the service provided (e.g. man-hours)


PersonalAccountNumber ::= OCTET STRING (SIZE(10))

ReceiptAuthenticator ::= OCTET STRING

ReceiptDistance ::= Int3Unsigned

ResultFin ::= OCTET STRING (SIZE(1))

ReceiptIccId ::= OCTET STRING

ReceiptObuId ::= OCTET STRING

ResultOp ::= INTEGER {
  correctTransaction                         (0),
  obeStatusNotAccepted                          (1),
  equipmentStatusNotAccepted                   (2),
  contractNotInWhiteList                         (3),
  contractIdentifierInBlackList                   (4),
  contractIdentifierNotCorrect                    (5),
  expiredContract                                (6),
  contractRestrictionsNotFulfilled               (7),
  claimedVehicleCharacteristicsNotValid            (8),
  vehicleClassAuthenticationFailed               (9),
  entryVehicleClassDifferentFromExitVehicleClass (10),
  entryReceiptMissing                           (11),
  entryReceiptNotValid                          (12),
  entryTollStationNotValid                       (13),
  equipmentNotCertified                         (14),
  timeDifference                                 (15),
  accessCredentialsNotAccepted                   (16),
  contractAuthenticatorNotAccepted               (17),
  receiptAuthenticatorNotAccepted                (18),
  claimedVehicleCharacteristicsMissing          (19),
  paymentMeansNotAccepted                        (20),
  paymentAuthenticatorNotAccepted                (21),
  paymentMeansInBlackList                        (22),
  paymentMeansNotCorrect                         (23),
  expiredPaymentMeans                            (24),
  paymentMeansRestrictionsNotFulfilled           (25)
} (0..255)

ReceiptServiceSerialNumber ::= Int3Unsigned

ReceiptText ::= OCTET STRING

StationType ::= INTEGER {
  unspecified                  (0),
  closedEntryWithPayment       (1),
  closedEntryWithoutPayment    (2),
  closedTransit                (3),
  closedExit                   (4),
  closedCredit                 (5),
  mixed                        (6),
  passage                      (7),
  checkpoint                   (8),
  reload                       (9),
  reservedForFutureCENUse1     (10),
  reservedForFutureCENUse2     (11),
  reservedForFutureCENUse3     (12),
  reservedForFutureCENUse4     (13),
  privateUse5                  (14),
  privateUse6                  (15)
} (0..15)

TariffClassId ::= Int4Unsigned -- default TariffClassId = 0

Time ::= Int4Unsigned

TimeClassId ::= Int2Unsigned

TimeUnit ::= INTEGER {
  seconds   (0),
  minutes   (1),
  hours     (2),
  days      (3),
  months    (4)
  -- (5-127) are reserved for future CEN use
  -- (128-255) are reserved for private use
}(0..255)

TrailerType::= INTEGER {
  notPresent    (0),
  trailer       (1),
  semitrailer   (2)
} (0..31)

TyreConfiguration ::= INTEGER {
  notSpecified     (0),
  singleTyre       (1), -- single tyre on all axles
  dualTyres        (2), -- dual tyres on at least one axle
  reservedForUse   (3) -- reserved for future CEN/ISO use
} (0..3)

UserClassId ::= Int1Unsigned

VehicleAuthenticator ::= OCTET STRING

VehicleClass ::= Int1Unsigned

VehicleCurrentMaxTrainWeight ::= Int2Unsigned

VehicleTotalDistance ::= Int4Unsigned

VehicleWeightLaden ::= Int2Unsigned

Weekday ::= INTEGER {
  reserved   (0),
  monday     (1),
  tuesday    (2),
  wednesday  (3),
  thursday   (4),
  friday     (5),
  saturday   (6),
  sunday     (7)
} (0..7)

-- Clause 5.3  Single level data types

AbsolutePosition2d ::= SEQUENCE {
  gnssLon   EcfLongitude,
  gnssLat   EcfLatitude
}

AbsolutePosition3d ::= SEQUENCE {
  longitude   EcfLongitude,
  latitude    EcfLatitude,
  altitude    EcfAltitude OPTIONAL
}

AxleWeightLimit ::= SEQUENCE {
  axleNumber             Int1Unsigned,
  maxLadenWeightOnAxle   Int2Unsigned
}

AxleWeightLimits ::= SEQUENCE {
  maxLadenweightOnAxle1   Int2Unsigned,
  maxLadenweightOnAxle2   Int2Unsigned,
  maxLadenweightOnAxle3   Int2Unsigned,
  maxLadenweightOnAxle4   Int2Unsigned,
  maxLadenweightOnAxle5   Int2Unsigned
}

DateCompact ::= SEQUENCE {
  year   INTEGER (1990..2117),
  month  INTEGER (1..12),
  day    INTEGER (1..31)
}

DieselEmissionValues ::= SEQUENCE {
  particulate      Particulate,
  absorptionCoeff  Int2Unsigned
}

DriverCharacteristics ::= SEQUENCE {
  driverClass  Int1Unsigned,
  tripPurpose  Int1Unsigned
}

Distance ::= SEQUENCE {
  distanceValue   Int4Unsigned,
  distanceUnit    DistanceUnit DEFAULT kilometres
}

EcfDuration ::= SEQUENCE {
  durationValue     Int4Unsigned,
  timeUnit          TimeUnit DEFAULT seconds
}

EngineDetails ::= SEQUENCE {
  engineCapacity  Int2Unsigned,
  enginePower     Int2Unsigned
}

ExhaustEmissionValues ::= SEQUENCE {
  unitType        EmissionUnit,
  emissionCo      INTEGER (0..32767),
  emissionHc      Int2Unsigned,
  emissionNox     Int2Unsigned,
  emissionHcNox   Int2Unsigned
}

NumberOfAxles ::= SEQUENCE {
  trailerAxles   INTEGER (0..7),
  tractorAxles   INTEGER (0..7)
}

ObeId ::= SEQUENCE {
  manufacturerId   Int2Unsigned,
  equipmentObuId   EquipmentObuId
}

Particulate ::= SEQUENCE {
  unitType   EmissionUnit,
  value      INTEGER (0..32767)
}

PassengerCapacity ::= SEQUENCE {
  numberOfSeats            Int1Unsigned,
  numberOfStandingPlaces   Int1Unsigned
}

PaymentFee ::= SEQUENCE {
  paymentFeeAmount   Int2Unsigned,
  paymentFeeUnit     PayUnit
}

Period ::= SEQUENCE {
  beginOfPeriod    GeneralizedTime,
  endOfPeriod      GeneralizedTime
}

Provider ::= SEQUENCE {
  countryCode          CountryCode,
  providerIdentifier   IssuerIdentifier
}

RelativePosition3d ::= SEQUENCE {
  longitude   Int2Signed,
  latitude    Int2Signed,
  altitude    Int2Signed OPTIONAL
}

SessionClass ::= SEQUENCE {
  sessionTariffClass   Int1Unsigned,
  sessionClaimedClass  Int1Unsigned
}

SessionLocation ::= SEQUENCE {
  ascendingKilometrage   BOOLEAN,
  laneCodeNumber         INTEGER(0..127)
}

SignedValue ::= CHOICE {
  positive   INTEGER (0..8388607),
  negative   INTEGER (-8388608..-1)
}

SoundLevel ::= SEQUENCE {
  soundStationary   Int1Unsigned,
  soundDriveBy      Int1Unsigned
}

TimeCompact ::= SEQUENCE {
  hours       INTEGER (0..23),
  mins        INTEGER (0..59),
  doubleSecs  INTEGER (0..30)
}

TrailerDetails::= SEQUENCE {
  trailerType   TrailerType,
  trailerAxles  INTEGER (0..7)
}

-- Clause 5.4  Two level data types

AxlesWeightLimits ::= SEQUENCE OF AxleWeightLimit


ChargeObjectId ::= SEQUENCE {
  chargeObjectOperator      Provider OPTIONAL,
  chargeObjectDesignation   Int4Unsigned
}

ContractValidity ::= SEQUENCE {
  contractRestrictions   OCTET STRING (SIZE(4)),
  contractExpiryDate     DateCompact
}

DateAndTime ::= SEQUENCE {
  timeDate      DateCompact,
  timeCompact   TimeCompact
}

EnvironmentalCharacteristics::= SEQUENCE {
  euroValue    EuroValue,
  copValue     CopValue
}

Lpn::= SEQUENCE {
  countryCode      CountryCode,
  alphabetIndicator   ENUMERATED {
    latinAlphabetNo1         (1),
    latinAlphabetNo2         (2),
    latinAlphabetNo3         (3),
    latinAlphabetNo4         (4),
    latinCyrillicAlphabet    (5),
    latinArabicAlphabet      (6),
    latinGreekAlphabet       (7),
    latinHebrewAlphabet      (8),
    latinAlphabetNo5         (9),
    latinAlphabetNo6         (10),
    twoOctetBMP                (11),
    fourOctetCanonical       (12),
    reservedForUse1          (13),
    reservedForUse2          (14),
    reservedForUse3          (15),
    reservedForUse4          (16),
    reservedForUse5          (17),
    reservedForUse6          (18),
    reservedForUse7          (19),
    reservedForUse8          (20),
    reservedForUse9          (21),
    reservedForUse10         (22),
    reservedForUse11         (23),
    reservedForUse12         (24),
    reservedForUse13         (25),
    reservedForUse14         (26),
    reservedForUse15         (27),
    reservedForUse16         (28),
    reservedForUse17         (29),
    reservedForUse18         (30),
    reservedForUse19         (31),
    reservedForUse20         (32),
    reservedForUse21         (33)
   },
  licencePlateNumber  OCTET STRING
}

PaymentMeans ::= SEQUENCE {
  personalAccountNumber    PersonalAccountNumber,
  paymentMeansExpiryDate   DateCompact,
  pamentMeansUsageControl  OCTET STRING(SIZE(2))
}

PaymentMeansBalance ::= SignedValue

Point ::= CHOICE {
  pointIdentifier            Int4Unsigned,
  absolutePointCoordinates   AbsolutePosition3d,
  relativePointCoordinates   RelativePosition3d
}

PurseBalance ::= SEQUENCE {
  purseValue   SignedValue,
  purseUnit    PayUnit
}

TrailerCharacteristics ::= SEQUENCE {
  trailerDetails         TrailerDetails,
  trailerMaxLadenWeight  Int2Unsigned,
  trailerWeightUnladen   Int2Unsigned
}

ValidityOfContract ::= SEQUENCE {
  issuerRestrictions   OCTET STRING (SIZE(2)),
  contractExpiryDate   DateCompact
}

VehicleAxlesNumber ::= SEQUENCE {
  tyreConfiguration  TyreConfiguration,
  numberOfAxles      NumberOfAxles
}

VehicleDimensions ::= SEQUENCE {
  vehicleLengthOverall   Int1Unsigned,
  vehicleHeigthOverall   Int1Unsigned,
  vehicleWidthOverall    Int1Unsigned
}

VehicleWeightLimits ::= SEQUENCE {
  vehicleMaxLadenWeight       Int2Unsigned,
  vehicleTrainMaximumWeight   Int2Unsigned,
  vehicleWeightUnladen        Int2Unsigned
}

-- Clause 5.5  Three level data types

EfcContextMark ::= SEQUENCE {
  contractProvider    Provider,
  typeOfContract      OCTET STRING (SIZE(2)),
  contextVersion      INTEGER(0..127,...)
}

ReceiptContract ::= SEQUENCE {
  sessionContractProvider       Provider,
  sessionTypeOfContract         OCTET STRING(SIZE(2)),
  sessionContractSerialNumber   Int4Unsigned
}

ReceiptData ::= SEQUENCE {
  sessionTime                DateAndTime,
  sessionServiceProvider     Provider,
  locationOfStation          Int2Unsigned,
  sessionLocation            SessionLocation,
  sessionType                Int1Unsigned,
  sessionResult              ResultOp,
  sessionTariffClass         Int1Unsigned,
  sessionClaimedClass        Int1Unsigned,
  sessionFee                 PaymentFee,
  sessionContractProvider    Provider,
  sessionTypeOfContract      OCTET STRING (SIZE(2)),
  sessionContextVersion      INTEGER (0..127,...),
  receiptDataAuthenticator   OCTET STRING(SIZE(4))
}

ReceiptFinancialPart ::= SEQUENCE {
  personalAccountNumber          PersonalAccountNumber,
  sessionPaymentFee              PaymentFee,
  sessionCurrentBalance          PurseBalance,
  receiptFinancialSerialNumber   Int4Unsigned
}

ReceiptServicePart ::= SEQUENCE {
  sessionTime                DateAndTime,
  sessionServiceProvider     Provider,
  stationLocation            INTEGER(0..1048575),
  sessionLocation            BIT STRING (SIZE(8)),
  typeOfSession              StationType,
  sessionResultOperational   ResultOp,
  sessionResultFinancial     ResultFin
}

UserId ::= SEQUENCE {
  pan                    PersonalAccountNumber OPTIONAL,
  contractSerialNumber   ContractSerialNumber OPTIONAL,
  licencePlateNumber     Lpn OPTIONAL,
  obeId                  ObeId OPTIONAL,
  iccId                  EquipmentIccId OPTIONAL
}( WITH COMPONENTS {..., pan PRESENT }|
   WITH COMPONENTS {..., contractSerialNumber PRESENT} |
   WITH COMPONENTS {..., licencePlateNumber PRESENT} |
   WITH COMPONENTS {..., obeId PRESENT} |
   WITH COMPONENTS {..., iccId PRESENT})

VehicleAxles ::= SEQUENCE {
  vehicleFirstAxleHeight    Int1Unsigned,
  vehicleAxlesNumber        VehicleAxlesNumber
}

VehicleSpecificCharacteristics ::= SEQUENCE {
  environmentalCharacteristics    EnvironmentalCharacteristics,
  engineCharacteristics           EngineCharacteristics,
  descriptiveCharacteristics      DescriptiveCharacteristics,
  futureCharacteristics           FutureCharacteristics
}

-- Clause 5.6  Complex data types

AggregatedSingleTariffClassSession ::= SEQUENCE {
  timePeriodCovered        Period OPTIONAL,
  currentTariffClass       TariffClassDescription OPTIONAL,
  vehicleDescription       VehicleDescription OPTIONAL,
  totalDistanceCovered     Distance OPTIONAL,
  numberOfDetectedEvents   Int2Unsigned OPTIONAL,
  obeStatus                Int1Unsigned OPTIONAL,
  feeExclVat               PaymentFee OPTIONAL,
  sumVat                   PaymentFee OPTIONAL,
   ...
}( WITH COMPONENTS {..., timePeriodCovered PRESENT }|
   WITH COMPONENTS {..., currentTariffClass PRESENT}|
   WITH COMPONENTS {..., vehicleDescription PRESENT}|
   WITH COMPONENTS {..., totalDistanceCovered PRESENT}|
   WITH COMPONENTS {..., numberOfDetectedEvents PRESENT}|
   WITH COMPONENTS {..., obeStatus PRESENT}|
   WITH COMPONENTS {..., feeExclVat PRESENT}|
   WITH COMPONENTS {..., sumVat PRESENT})

DetectedChargeObject ::= SEQUENCE {
  chargeObjectId           ChargeObjectId,
  subObjectNumber          Int4Unsigned OPTIONAL,
  timeWhenUsed             GeneralizedTime OPTIONAL,
  mileageWhenUsed          Distance OPTIONAL,
  currentTariffClass       TariffClassDescription OPTIONAL,
  vehicleDescription       VehicleDescription OPTIONAL,
  obeStatus                Int1Unsigned OPTIONAL,
  feeExclVat               PaymentFee OPTIONAL,
  sumVat                   PaymentFee OPTIONAL,
  chargeObjDetectionMode   DetectionMode OPTIONAL,
  ...
}

TariffClassDescription ::= SEQUENCE {
  tariffClassId          TariffClassId DEFAULT 0,
  localVehicleClassId    LocalVehicleClassId OPTIONAL,
  timeClassId            TimeClassId OPTIONAL,
  locationClassId        LocationClassId OPTIONAL,
  userClassId            UserClassId OPTIONAL
}

VehicleDescription ::= SEQUENCE {
  vehicleLPNr                    Lpn OPTIONAL,
  axles                          VehicleAxles OPTIONAL,
  class                          VehicleClass OPTIONAL,
  dimensions                     VehicleDimensions OPTIONAL,
  specificCharacteristics        VehicleSpecificCharacteristics OPTIONAL,
  ladenWeight                    VehicleWeightLaden OPTIONAL,
  weightLimits                   VehicleWeightLimits OPTIONAL,
  trailerCharacteristics         TrailerCharacteristics OPTIONAL,
  vehicleCurrentMaxTrainWeight   VehicleCurrentMaxTrainWeight OPTIONAL,
  actualNumberOfPassengers       ActualNumberOfPassengers OPTIONAL,
  axleWeightLimits               AxleWeightLimits OPTIONAL,
  dieselEmissionValues           DieselEmissionValues OPTIONAL,
  driverCharacteristics          DriverCharacteristics OPTIONAL,
  engineDetails                  EngineDetails OPTIONAL,
  exhaustEmissionValues          ExhaustEmissionValues OPTIONAL,
  passengerCapacity              PassengerCapacity OPTIONAL,
  soundLevel                     SoundLevel OPTIONAL,
   ...
}( WITH COMPONENTS {..., vehicleLPNr PRESENT }|
   WITH COMPONENTS {..., axles PRESENT }|
   WITH COMPONENTS {..., class PRESENT}|
   WITH COMPONENTS {..., dimensions PRESENT}|
   WITH COMPONENTS {..., specificCharacteristics PRESENT}|
   WITH COMPONENTS {..., ladenWeight PRESENT}|
   WITH COMPONENTS {..., weightLimits PRESENT}|
   WITH COMPONENTS {..., trailerCharacteristics PRESENT}|
   WITH COMPONENTS {..., vehicleCurrentMaxTrainWeight PRESENT}|
   WITH COMPONENTS {..., actualNumberOfPassengers PRESENT}|
   WITH COMPONENTS {..., axleWeightLimits PRESENT }|
   WITH COMPONENTS {..., dieselEmissionValues PRESENT}|
   WITH COMPONENTS {..., driverCharacteristics PRESENT}|
   WITH COMPONENTS {..., engineDetails PRESENT}|
   WITH COMPONENTS {..., exhaustEmissionValues PRESENT}|
   WITH COMPONENTS {..., passengerCapacity PRESENT}|
   WITH COMPONENTS {..., soundLevel PRESENT})

END

-- Use of this module defined in SAE J3217/R
-- Latest document release for this module is Jan 2024
-- Filename: J3217-R-RoadUserChargingConfigMsg-2024-rel-v1.1.1.asn
--

RoadUserChargingConfigMessage
{joint-iso-itu-t (2) country (16) us (840) organization (1) sae (114566)
v2x-communications (1) technical-committees (1) tolling-applications (9) technical-reports (1)
j3217 (3217) slash-r (28) asn1-module (1) roadUserChargingConfigMessage (3)
version-1 (1) version-minor-1 (1)}

DEFINITIONS AUTOMATIC TAGS ::=
BEGIN

IMPORTS
    EventRecurrence
        FROM RoadSafetyMessage {joint-iso-itu-t (2) country (16) us (840) organization (1)
      sae (114566) v2x-communications (1) technical-committees (1) v2x-core (5)
      technical-reports (1) j2945 (2945) slash-4 (4) asn1-module (1) roadSafetyMessage (39)
      version-1 (1) version-minor-1 (1)}
    ValidRegion
        FROM TravelerInformation {joint-iso-itu-t (2) country (16) us (840) organization (1)
      sae (114566) v2x-communications (1) technical-committees (1) v2x-core (5)
      technical-reports (1) j2735 (2735) part-0 (0) asn1-module (1) travelerInformation (20)
      version-1 (1) version-minor-1 (1)}
    ChargesTable,
    VehicleTypes,
    TollAdvertisementMessage
        FROM TollAdvertisementMessage {joint-iso-itu-t (2) country (16) us (840) organization (1)
      sae (114566) v2x-communications (1) technical-committees (1) tolling-applications (9)
      technical-reports (1) j3217 (3217) asn1-module (1) tollAdvertisementMessage (0)
      version-1 (1) version-minor-1 (1)}
    DescriptiveName,
    DDateTime
        FROM Common {joint-iso-itu-t (2) country (16) us (840) organization (1)
        sae (114566) v2x-communications (1) technical-committees (1) v2x-core (5)
        technical-reports (1) j2735 (2735) part-0 (0) asn1-module (1) common (38)
        version-1 (1) version-minor-1 (1)}
    CountryCode,
    PaymentFee
        FROM EfcDataDictionary {iso(1) standard(0) 17573 dd(3)
        version1(1)};

RoadUserChargingConfigMessage ::= SEQUENCE {
    chargerInfoTable    SEQUENCE (SIZE(1..999, ...)) OF ChargerInfo,
    ...
}

ChargerInfo ::= SEQUENCE {
    chargerID           OBJECT IDENTIFIER,
    -- ID of the road charging entity
    descriptiveName     DescriptiveName     OPTIONAL, -- From J2735 Common
    timeStamp           DDateTime           OPTIONAL,
    -- Time the config was created
    chargingConfig      ChargingConfig,
    -- Geo areas and road segments subject to road use charges
    ...
}

ChargingConfig ::= SEQUENCE {
    configInfo      ConfigInfo,
    reportSched     ENUMERATED {hourly (0), weekly (1), monthly (2), quarterly (3), ...},

    -- Charges may be incurred by any or all methods defined here:
    -- - At the primary-region level (e.g., US state, Canada province, Mexico state, etc.)
    -- - At the sub-region level (e.g., county, municipality, etc.)
    -- - At any defined polygonal region or road segment.
    byPrimaryRegion PrimaryRegionChargingInfo,
    bySubRegion     SEQUENCE (SIZE (1..999, ...)) OF SubRegionChargingInfo  OPTIONAL,
    byAreaOrSegment AreaOrSegmentChargingInfo                               OPTIONAL,
    ...
}

ConfigInfo ::= SEQUENCE {
    configID               INTEGER (0..64, ...),
    configVersion          INTEGER (0..64, ...),
    startDate              DDateTime,
    expirationDate         DDateTime,
    configurationFeeType   ENUMERATED {excluded (0),
                                replacesOtherCharges (1),
                                addedToOtherCharges (2),
                                ...},
    ...
}

PrimaryRegionChargingInfo ::= SEQUENCE {
    primaryRegionCountry    CountryCode, -- From ISO17573-EfcDataDictionary.asn
    chargingPrimaryRegion   CHOICE {
        state   PrimaryRegionState,
        ... -- Extensible to support future primaryRegion types (other than states)
    },
    ...
}

PrimaryRegionState ::= SEQUENCE {
    usCanMexState   IA5String (SIZE(2,...)),
    -- Two-char subdivision code for US states, Canada provinces or Mexico states,
    -- as defined by the two-letter code in ISO-3166-2
    -- Use if CountryCode indicates US, Canada, or Mexico
    chargingFees    ChargingFees        OPTIONAL,
    ...
}

SubRegionChargingInfo ::= SEQUENCE {
    subRegion       OBJECT IDENTIFIER,  -- Relative OID (to chargerID)
    chargingFees    ChargingFees,
    ...
}

AreaOrSegmentChargingInfo ::= SEQUENCE {
    chargingAreaOrSegment   SEQUENCE (SIZE(1..999, ...)) OF ChargingAreaOrSegment,
    ...
}

ChargingAreaOrSegment ::= CHOICE {
    area    Area,
    segment Segment,
    ...
}

Area ::= SEQUENCE {
    areaID          OBJECT IDENTIFIER, -- Relative OID
    chargingArea    ValidRegion (WITH COMPONENTS {...,
                        extent ABSENT,
                        area (WITH COMPONENTS {...,
                            shapePointSet ABSENT
                        })
                    }),
    chargingFees    ChargingFees,
    ...
}

Segment ::= SEQUENCE {
    segmentID       OBJECT IDENTIFIER, -- Relative OID
    chargingSegment SEQUENCE (SIZE(1..999, ...)) OF TollAdvertisementMessage,
    -- From J3217 TAM
    chargingUnits   ChargingUnits   OPTIONAL, -- If present charge based on dist or time
    ...
}

ChargingFees ::= SEQUENCE {
    chargingSchedule   SEQUENCE      -- Date/time periods for which charge applies.
       (SIZE(1..5, ...)) OF EventRecurrence OPTIONAL,   -- From J2945/4  RSM
        -- Up to 5 charging periods may be defined.
    chargesTable    ChargesTable,   -- From J3217 TAM
    chargingUnits   ChargingUnits,
    ...
}

ChargingUnits ::= CHOICE {
    driven    Driven,
    parked    Parked,
    ...
}

Driven ::= ENUMERATED {
    perMin      (0),
    perHour     (1),
    perDay      (2),
    perDistMile (3),
    perDistKilo (4),
    ...
}

Parked ::= ENUMERATED {
    perMin      (0),
    perHour     (1),
    perDay      (2),
    ...
}

END

-- Use of this module defined in SAE J3217/R
-- Latest document release for this module is Jan 2024
-- Filename: J3217-R-RoadUserChargingReportMsg-2024-rel-v1.1.asn
--

RoadUserChargingReportMessage
{joint-iso-itu-t (2) country (16) us (840) organization (1) sae (114566)
v2x-communications (1) technical-committees (1) tolling-applications (9) technical-reports (1)
j3217 (3217) slash-r (28) asn1-module (1) roadUserChargingReportMessage (4)
version-1 (1) version-minor-1 (1)}

DEFINITIONS AUTOMATIC TAGS ::=
BEGIN

IMPORTS
    VehicleTypes
        FROM TollAdvertisementMessage {joint-iso-itu-t (2) country (16) us (840)
        organization (1) sae (114566) v2x-communications (1) technical-committees (1)
        tolling-applications (9) technical-reports (1) j3217 (3217) asn1-module (1)
        tollAdvertisementMessage (0) version-1 (1) version-minor-1 (1)}
    VehicleId
        FROM TollUsageMessage {joint-iso-itu-t (2) country (16) us (840)
        organization (1) sae (114566) v2x-communications (1) technical-committees (1)
        tolling-applications (9) technical-reports (1) j3217 (3217) asn1-module (1)
        tollUsageMessage (1) version-1 (1) version-minor-1 (1)}
    DistanceUnits
        FROM TravelerInformation {joint-iso-itu-t (2) country (16) us (840)
        organization (1) sae (114566) v2x-communications (1) technical-committees (1)
        v2x-core (5) technical-reports (1) j2735 (2735) part-0 (0) asn1-module (1)
        travelerInformation (20) version-1 (1) version-minor-1 (1)}
    DescriptiveName,
    DDateTime
        FROM Common {joint-iso-itu-t (2) country (16) us (840) organization (1)
        sae (114566) v2x-communications (1) technical-committees (1) v2x-core (5)
        technical-reports (1) j2735 (2735) part-0 (0) asn1-module (1) common (38)
        version-1 (1) version-minor-1 (1)}
    PaymentFee,
    VehicleDescription
        FROM EfcDataDictionary {iso(1) standard(0) 17573 dd(3)
        version1(1)};

RoadUserChargingReportMessage ::= SEQUENCE {
    usageReport             UsageReport,
    serviceProviderData     OCTET STRING (SIZE(1024))   OPTIONAL,
    ...
}

UsageReport ::= CHOICE {
    feeReport               FeeReport,
    -- Fee report is not itemized and includes a user/vehicle identifier
    itemizedPaymentReport   ItemizedPaymentReport,
    -- Itemized report does not include a user/vehicle identifier
    ...
}

-- This form of the payment report includes information identifiable to
-- a specific user (as opposed to the itemized report which does not.)
FeeReport ::= SEQUENCE {
    userData    UserData,
    fees        UserFeeInfo,
    ...
}

UserData ::= SEQUENCE {
    timeStamp               DDateTime,
    svcProvID               OBJECT IDENTIFIER, -- Service provider ID
    vehicleID               VehicleId,         -- From J3217 TUM
    vehicleType             VehicleTypes,      -- From J3217 TAM
    vehicleDescription      VehicleDescription  OPTIONAL, -- From ISO 17573
    ...
}

UserFeeInfo ::= SEQUENCE {
    fee             PaymentFee,     -- From ISO 17573
    -- Fee the OBE intends to pay.
    -- Corresponds to the fees incurred according to the RUC Config received
    -- from the RUC service provider
    timePeriod      TimePeriod,
    ...
}

-- This form of the payment report does NOT include information identifiable
-- to a specific user. Also see FeeReport.
ItemizedPaymentReport ::= SEQUENCE {
    timeStamp       DDateTime,
    timePeriod      TimePeriod,
    -- Time period over which charges accrue, and are then due for payment
    svcProvID       OBJECT IDENTIFIER, -- Service provider ID
    chargerData     SEQUENCE (SIZE(1..999, ...)) OF ItemizedChargerData,
    ...
}

ItemizedChargerData ::= SEQUENCE {
    chargerID           OBJECT IDENTIFIER,
    -- ID of the road charging entity, corresponds with chargerID provided in config
    chargingDescription DescriptiveName     OPTIONAL, -- From J2735 Common
    configID            INTEGER (0..64,...) OPTIONAL,
    tripInfo            TripInfo            OPTIONAL,
    totalPaidToCharger  PaymentFee,                   -- From ISO 17573
    ...
}

-- Contains info pertaining to the distance traveled and duration of time it took
TripInfo ::= SEQUENCE {
    distanceTraveled    INTEGER (1..65535,...)  OPTIONAL, -- In DistanceUnits
    distanceUnits       DistanceUnits           OPTIONAL,
    timeTraveled        INTEGER (1..600000,...) OPTIONAL,
    -- Time duration in minutes. Up to 600,000 minutes, 10,000 hours
    -- Rounded down to nearest minute
    ...
}
(WITH COMPONENTS {...,distanceTraveled, distanceUnits PRESENT} |
 WITH COMPONENTS {...,timeTraveled PRESENT})


-- Time period over which charges accrue, and are then due for payment
-- Typically 30-days
TimePeriod ::= SEQUENCE {
    startTime       DDateTime,
    endTime         DDateTime,
    ...
}

END
-- Use of this module defined in SAE J3217
-- Latest document release for this module is Jun 2022
-- Filename: J3217-TollAdvertisementMsg-2024-rel-v1.1.asn
--

TollAdvertisementMessage
{joint-iso-itu-t (2) country (16) us (840) organization (1) sae (114566)
v2x-communications (1) technical-committees (1) tolling-applications (9)
technical-reports (1) j3217 (3217) asn1-module (1) tollAdvertisementMessage (0)
version-1 (1) version-minor-1 (1)}

DEFINITIONS AUTOMATIC TAGS ::=
BEGIN

IMPORTS
    GenericLane
        FROM MapData {joint-iso-itu-t (2) country (16) us (840) organization (1)
        sae (114566) v2x-communications (1) technical-committees (1) v2x-core (5)
        technical-reports (1) j2735 (2735) part-0 (0) asn1-module (1) mapData (8)
        version-1 (1) version-minor-1 (1)}
    DescriptiveName,
    LaneID,
    DDateTime,
    MsgCount,
    RegulatorySpeedLimit,
    LaneWidth,
    Position3D
        FROM Common {joint-iso-itu-t (2) country (16) us (840) organization (1)
        sae (114566) v2x-communications (1) technical-committees (1) v2x-core (5)
        technical-reports (1) j2735 (2735) part-0 (0) asn1-module (1) common (38)
        version-1 (1) version-minor-1 (1)}
    EngineCharacteristics,
    PaymentFee
        FROM EfcDataDictionary {iso(1) standard(0) 17573 dd(3)
        version1(1)};

TollAdvertisementMessage ::= SEQUENCE {
-- Toll Advertisement Message (TAM) is message broadcast by RSEs about the variable
-- Toll Road Topology with accompanying Toll Rates
    tollChargesTable    TollChargesTable,
    tollAdvInfo         TollAdvertisementInfo           OPTIONAL,
    ...
}

TollAdvertisementInfo ::= SEQUENCE {
    tamSequenceNum      MsgCount,
    -- Increments only if TAM contents have changed (or any TAMs have changed)
    totalTams           INTEGER (1..10, ...),
    -- If multiple TAMs are used, they can be linked together (see tamNum)
    tamNum              INTEGER (1..10, ...),
    -- Identifies each TAM in a set. Up to ten TAMs can be linked together
    tollChargerInfo     TollChargerInfo,
    -- Includes TollCharger and TollPoint identifiers
    timestamp           DDateTime,
    -- Time of Generation (prior to signing)
    tumInstructions     TumInstructions     OPTIONAL,
    -- Num of loc/timestamp pairs to send in TUM
    tollPointMap        TollPointMap,
    tumPublicKey        OCTET STRING (SIZE(32)),
    -- Replicated from the applicable portion of IEEE 1609.2 EccP256CurvePoint
    ackPolicy           AckPolicy,
    lastTollPtDataReq   BOOLEAN OPTIONAL,
    ...
}

TumInstructions ::= SEQUENCE {
    maxNumOfLocTimeStamps   INTEGER (1..5, ...),
    locTimeStampRate        INTEGER (1..10,...), -- In Hz (1=once per sec, etc._)
    ...
}

AckPolicy ::= SEQUENCE {
    timeout         INTEGER (100..10000), -- in milliseconds
    numOfRetries    INTEGER (1..5, ...),  -- Give up sending TUM after numOfRetries tries
    ...
}

TollChargesTable ::= SEQUENCE {
    tollTypeCharge      CHOICE {
        pointCharges            ChargesTable,
        -- All lanes are the same fee per vehicle type
        perLaneCharges          SEQUENCE (SIZE(1..64, ...)) OF LaneChargesTable,
        -- Per lane, per vehicle charges allowed (still a point charge)
        closedNetworkCharges    SEQUENCE (SIZE(1..64, ...)) OF ClosedNetworkChargesTable,
        -- Closed network, no per lane charges allowed
        timeBasedCharges    TimeChargesTable,
        ...
    },
    ...
}

LaneChargesTable ::= SEQUENCE {
    laneId          LaneID,
    chargesTable    ChargesTable,
    ...
}

ClosedNetworkChargesTable ::= CHOICE {
    entryChargesTable   EntryChargesTable,
    exitChargesTable    ExitChargesTable,
    ...
}

EntryChargesTable ::= SEQUENCE {
    exitInfo        ExitInfo,
    --Exit points provided when entering the closed network
    chargesTable    ChargesTable,
    ...
}

ExitChargesTable ::= SEQUENCE {
    entryInfo       TollPointID     OPTIONAL,
    --Entry points prior to this toll point
    chargesTable    ChargesTable,
    ...
}

ExitInfo ::= SEQUENCE {
    exitNumber      INTEGER (1..999, ...),
    exitLetter      INTEGER (65..90)    OPTIONAL,
    -- Use ASCII character code for a single letter in the range of A to Z
    tollPointID     TollPointID         OPTIONAL,
    ...
}

TimeChargesTable ::= SEQUENCE {
    maxTime         INTEGER (1..1440),
    -- In minutes, up to 24 hours, used to compute max fee
    chargesTable    ChargesTable,
    -- Fee indicates charge per minute
    ...
}

ChargesTable ::= CHOICE {
    vehTypeBased        VehTypeChargesTable,
    numAxlesBased       AxlesChargesTable,
    weightBased         WeightChargesTable,
    ...
}

VehTypeChargesTable ::= SEQUENCE (SIZE(1..13, ...)) OF VehTypeCharges

VehTypeCharges ::= SEQUENCE {
    vehType         VehicleTypes,
    charges         PaymentFee,
    specialCharges  SpecialCharges OPTIONAL,
    ...
}

VehicleTypes ::= ENUMERATED {
    motorcycles                 (1),
    passengerCars               (2),
    fourTireSingleUnit          (3),
    buses                       (4),
    twoAxleSixTireSingleUnit    (5),
    threeAxleSingleUnit         (6),
    fourOrMoreAxleSingleUnit    (7),
    fourOrLessAxleSingleTrailer (8),
    fiveAxleTractorSemitrailer  (9),
    sixOrMoreAxleSingleTrailer  (10),
    fiveOrLessAxleMultiTrailer  (11),
    sixAxleMultiTrailer         (12),
    sevenOrMoreAxleMultiTrailer (13),
    ...
} -- 13 FHWA veh classes

SpecialCharges ::= SEQUENCE {
    hov2Charge              PaymentFee      OPTIONAL,
    hov3Charge              PaymentFee      OPTIONAL,
    hov4Charge              PaymentFee      OPTIONAL,
    hov5PlusCharge          PaymentFee      OPTIONAL,
    cleanAirCharge          PaymentFee      OPTIONAL,
    operatorDefined         OperatorDefined OPTIONAL,
    engineCharacteristics   EngineCharacteristics OPTIONAL, -- Imported from ISO 17573
    ...
}

-- Up to 16 toll-charger defiend specialCharges categories
OperatorDefined ::= SEQUENCE {
    opDefCharge1    PaymentFee OPTIONAL,
    opDefCharge2    PaymentFee OPTIONAL,
    opDefCharge3    PaymentFee OPTIONAL,
    opDefCharge4    PaymentFee OPTIONAL,
    opDefCharge5    PaymentFee OPTIONAL,
    opDefCharge6    PaymentFee OPTIONAL,
    opDefCharge7    PaymentFee OPTIONAL,
    opDefCharge8    PaymentFee OPTIONAL,
    opDefCharge9    PaymentFee OPTIONAL,
    opDefCharge10   PaymentFee OPTIONAL,
    opDefCharge11   PaymentFee OPTIONAL,
    opDefCharge12   PaymentFee OPTIONAL,
    opDefCharge13   PaymentFee OPTIONAL,
    opDefCharge14   PaymentFee OPTIONAL,
    opDefCharge15   PaymentFee OPTIONAL,
    opDefCharge16   PaymentFee OPTIONAL,
    ...
}

-- This table can support from 1 to 10 weight ranges
-- Weight ranges are not fixed, they can vary from message to message
WeightChargesTable ::= SEQUENCE (SIZE(1..10), ...) OF WeightCharges

WeightCharges ::= CHOICE {
    totalWeightCharges      TotalWeightCharges,
    perAxleWeightCharges    PerAxleWeightCharges,
    ...
}

TotalWeightCharges ::= SEQUENCE {
    weightLimit         INTEGER (0..16777215), -- In units indicated
    weightLimitUnits    ENUMERATED {pounds, kilograms, ...},
    weightCharge        PaymentFee,
    ...
}

PerAxleWeightCharges ::= SEQUENCE {
    totalWeightLimit        INTEGER (0..16777215), -- In units indicated
    maxLadenWeightOnAxle    INTEGER (0..65535),
    weightLimitUnits        ENUMERATED {pounds, kilograms, ...},
    axleWeightCharge        PaymentFee,
    ...
}

-- This table can support from 1 to 10 axle limit ranges
-- Axle limit ranges are not fixed, they can vary from message to message
AxlesChargesTable ::= SEQUENCE (SIZE(2..10, ...)) OF AxlesCharges

AxlesCharges ::= SEQUENCE {
    axlesLimit      INTEGER (2..10, ...),
    axlesCharge     PaymentFee,
    ...
}

TollPointMap ::= SEQUENCE {
    revisionNum         INTEGER (1..10, ...),
    referencePoint      Position3D,
    speedLimit          RegulatorySpeedLimit,   -- Regulatory speed limit
    laneWidth           LaneWidth,  --
    approachLanesMap    SEQUENCE (SIZE(1..64), ...) OF GenericLane
        (WITH COMPONENTS
            {..., name, ingressApproach, egressApproach, maneuvers, overlays ABSENT }),
    tollZoneLanesMap    SEQUENCE (SIZE(1..64), ...) OF GenericLane
        (WITH COMPONENTS
            {..., name, ingressApproach, egressApproach, maneuvers, overlays ABSENT }),
    ...
}

TollChargerInfo ::= SEQUENCE {
    tollChargerId       OBJECT IDENTIFIER,     -- OID of the entity charging the tolls
    tollPointId         TollPointID,
    descriptiveName     DescriptiveName OPTIONAL,
    ...
}

TollPointID ::= INTEGER (1..2048)

END

-- Use of this module defined in SAE J3217
-- Latest document release for this module is Jun 2022
-- Filename: J3217-TollUsageAckMsg-2024-rel-v1.1.asn
--

TollUsageAckMessage
{joint-iso-itu-t (2) country (16) us (840) organization (1) sae (114566)
v2x-communications (1) technical-committees (1) tolling-applications (9)
technical-reports (1) j3217 (3217) asn1-module (1) tollUsageAckMessage (2)
version-1 (1) version-minor-1 (1)}

DEFINITIONS AUTOMATIC TAGS ::=
BEGIN

IMPORTS
    MsgCount,
    TemporaryID
        FROM Common {joint-iso-itu-t (2) country (16) us (840) organization (1)
        sae (114566) v2x-communications (1) technical-committees (1) v2x-core (5)
        technical-reports (1) j2735 (2735) part-0 (0) asn1-module (1) common (38)
        version-1 (1) version-minor-1 (1)};

TollUsageAckMessage ::= SEQUENCE {
    tumAck      TumAck,
    ackMaxAge   INTEGER (100..10000, ...),
    -- In milliseconds, time window that indicates the max age of all corresponding TUMs
    ...
}

TumAck ::= SEQUENCE (SIZE(1..32)) OF TumAckHash

TumAckHash ::= SEQUENCE {
    signedTumHash   OCTET STRING (SIZE(32)) OPTIONAL,
    -- SHA-256 hash of the signed TumData
    tempId          TemporaryID,     -- From corresponding TUM
    tumSequenceNum  MsgCount,        -- From corresponding TUM
    ...
}
-- Up to 32 cars can be acked in one TumAck

END-- Use of this module defined in SAE J3217
-- Latest document release for this module is Jun 2022
-- Filename: J3217-TollUsageMsg-2024-rel-v1.1.asn
--

TollUsageMessage
{joint-iso-itu-t (2) country (16) us (840) organization (1) sae (114566)
v2x-communications (1) technical-committees (1) tolling-applications (9)
technical-reports (1) j3217 (3217) asn1-module (1) tollUsageMessage (1)
version-1 (1) version-minor-1 (1)}

DEFINITIONS AUTOMATIC TAGS ::=
BEGIN

IMPORTS
    VehicleTypes,
    TollChargerInfo,
    TollPointID
        FROM TollAdvertisementMessage {joint-iso-itu-t (2) country (16) us (840)
        organization (1) sae (114566) v2x-communications (1) technical-committees (1)
        tolling-applications (9) technical-reports (1) j3217 (3217) asn1-module (1)
        tollAdvertisementMessage (0) version-1 (1) version-minor-1 (1)}
    GenericLane
        FROM MapData {joint-iso-itu-t (2) country (16) us (840) organization (1)
        sae (114566) v2x-communications (1) technical-committees (1) v2x-core (5)
        technical-reports (1) j2735 (2735) part-0 (0) asn1-module (1) mapData (8)
        version-1 (1) version-minor-1 (1)}
    DescriptiveName,
    DDateTime,
    LaneID,
    Latitude,
    Longitude,
    Elevation,
    MinuteOfTheYear,
    MsgCount,
    Position3D,
    TemporaryID
        FROM Common {joint-iso-itu-t (2) country (16) us (840) organization (1)
        sae (114566) v2x-communications (1) technical-committees (1) v2x-core (5)
        technical-reports (1) j2735 (2735) part-0 (0) asn1-module (1) common (38)
        version-1 (1) version-minor-1 (1)}
    EngineCharacteristics,
    PaymentFee,
    UserId,
    VehicleDescription
        FROM EfcDataDictionary {iso(1) standard(0) 17573 dd(3)
        version1(1)};


TollUsageMessage ::= SEQUENCE {
-- Toll Usage Message (TUM) is a new message from OBE to indicate to RSE the
-- intent to use toll lane broadcasted in TAM Zone
    tollPointInfo       TollChargerInfo,    -- TC and TP IDs
    tempID              TemporaryID,
    tumSequenceNum      MsgCount,           -- Increments when retries occur
    tamSequenceNum      MsgCount,           -- Indicates the TAM being responded to
    tumHash             TumHash OPTIONAL,
    encryptedTumData    EncryptedTumData,   -- This portion will be encrypted
    ...
}

TumHash ::= OCTET STRING (SIZE(32)) -- SHA-256 hash of the plain text TumData
EncryptedTumData ::= OCTET STRING (SIZE(1..7000))
-- EncryptedTumData contains UPER-encoded TumData that is encrypted
-- 8000 octets is the max size of a 3GPP packet payload
-- 1000 is left for lower layer overhead

-- TumData gets UPER-encoded, encrypted and stored in EncryptedTumData for transmission
TumData ::= SEQUENCE {
    tollUserData                TollUserData,
    tollServiceProviderData     TollServiceProviderData OPTIONAL,
    ...
}

TollServiceProviderData ::= OCTET STRING (SIZE(1..1024, ...))

TollUserData ::= SEQUENCE {
    timeStamp           DDateTime,
    tspId               OBJECT IDENTIFIER,  -- OID of Toll Service Provider
    vehicleId           VehicleId,
    vehType             VehicleTypes        OPTIONAL,
    vehicleDescription  VehicleDescription  OPTIONAL,       -- Imported from ISO 17573
    vehAxlesAndWeight   VehicleAxlesAndWeightInfo OPTIONAL,
    numOccupants        INTEGER (2..5, ...)      OPTIONAL,
    -- Num of people in the vehicle if more than one, the value 5 indicates 5 or more
    entryTollPointId    TollPointID         OPTIONAL,
    entryTimeStamp      DDateTime           OPTIONAL,
    -- entryTollPointId and entryTimeStamp are used for closed networks
    locAndTimeStamps    LocAndTimeStamps    OPTIONAL,
    lastTollPoints      LastTollPointInfos  OPTIONAL,
    --Used by the TC to compute travel times
    charge              PaymentFee          OPTIONAL,
    ...
}

VehicleAxlesAndWeightInfo ::= SEQUENCE {
    vehNumAxles         INTEGER (1..10, ...),
    -- The value 10 indicates 10 or more axles
    vehWeightPerAxle    SEQUENCE (SIZE(1..10, ...)) OF INTEGER (0..65535),
    -- Provide weight for each axle specified in vehNumAxles
    vehTotalWeight      INTEGER (0..16777215),
    -- Includes tractor and trailer train, in units indicated
    vehWeightUnits      ENUMERATED {pounds, kilograms, ...},
    ...
}

VehicleId ::= SEQUENCE {
    vehicleIdentity     OCTET STRING (SIZE(16, ...)) OPTIONAL,
    licPlateState       IA5String (SIZE(2))          OPTIONAL,
    licPlateNumVeh      IA5String (SIZE(1..12, ...)) OPTIONAL,
    licPlateNumTrailer  IA5String (SIZE(1..12, ...)) OPTIONAL,
    -- Last trailer in a train if multiple trailers
    userId              UserId                       OPTIONAL, -- Imported from ISO 17573
    ...
}

LocAndTimeStamps ::= SEQUENCE (SIZE(1..5, ...)) OF LocAndTimeStamp

LocAndTimeStamp ::= SEQUENCE {
    latitude    Latitude,
    longitude   Longitude,
    elevation   Elevation   OPTIONAL,
    timeStamp   DDateTime,
    currentLane LaneID      OPTIONAL,
    ...
}

LastTollPointInfos ::= SEQUENCE (SIZE (1..5, ...)) OF LastTollPointInfo

LastTollPointInfo ::= SEQUENCE {
    tollChargerInfo     TollChargerInfo,
    -- Includes TollCharger and TollPoint identifiers
    timeStamp           DDateTime,
    -- Time of TUM transmission at previous toll point
    ...
}

END



-- Use of this module defined in SAE J3224
-- Latest document release for this module is Aug 2022
-- Filename: J3224-SensorDataSharingMessage-2024-rel-v1.1.asn
--

SensorDataSharingMessage
{joint-iso-itu-t (2) country (16) us (840) organization (1) sae (114566)
v2x-communications (1) technical-committees (1) v2x-vehicular-applications (8)
technical-reports (1) j3224 (3224) asn1-module (1) sensorDataSharingMessage (41)
version-1 (1) version-minor-1 (1)}

DEFINITIONS AUTOMATIC TAGS ::=
BEGIN

IMPORTS
    Acceleration,
    AccelerationSet4Way,
    BasicVehicleClass,
    DDateTime,
    Elevation,
    ElevationConfidence,
    ExteriorLights,
    Heading,
    HeadingConfidence,
    Latitude,
    Longitude,
    MsgCount,
    Position3D,
    PositionalAccuracy,
    PositionConfidenceSet,
    SemiMajorAxisAccuracy,
    SemiMinorAxisAccuracy,
    SemiMajorAxisOrientation,
    Speed,
    SpeedConfidence,
    TemporaryID,
    TimeConfidence,
    VehicleHeight,
    VehicleLength,
    VehicleSize,
    VehicleWidth,
    VerticalAcceleration,
    YawRate
        FROM Common {joint-iso-itu-t (2) country (16) us (840) organization (1) sae (114566)
      v2x-communications (1) technical-committees (1) v2x-core (5) technical-reports (1)
      j2735 (2735) part-0 (0) asn1-module (1) common (38)
      version-1 (1)  version-minor-1 (1)}
    Attachment,
    AttachmentRadius,
    PersonalDeviceUserType,
    PropelledInformation
        FROM PersonalSafetyMessage {joint-iso-itu-t (2) country (16) us (840) organization (1) sae (114566)
        v2x-communications (1) technical-committees (1) v2x-core (5) technical-reports (1)
        j2735 (2735) part-0 (0) asn1-module (1) personalSafetyMessage (21)
        version-1 (1) version-minor-1 (1)}
    AccelerationConfidence,
    YawRateConfidence
        FROM ProbeVehicleData {joint-iso-itu-t (2) country (16) us (840) organization (1) sae (114566)
        v2x-communications (1) technical-committees (1) v2x-core (5) technical-reports (1)
        j2735 (2735) part-0 (0) asn1-module (1) probeVehicleData (15)
        version-1 (1) version-minor-1 (1)};

SensorDataSharingMessage ::= SEQUENCE {
    msgCnt MsgCount,
    -- Sequence     number
    sourceID        TemporaryID,
    -- temporary vehicle ID / RSU ID. SDSM source.
    equipmentType   EquipmentType,
    -- Sender type
    sDSMTimeStamp   DDateTime,
    -- SDSM transmission time
    refPos          Position3D,
    -- Sender reference position
    refPosXYConf    PositionalAccuracy,
    refPosElConf    ElevationConfidence     OPTIONAL,
    objects DetectedObjectList
    -- detected     objects
}

EquipmentType ::= ENUMERATED{
    unknown (0),
    rsu     (1),
    obu     (2),
    vru     (3),
    ...
}

DetectedObjectList::= SEQUENCE (SIZE(1..256)) OF DetectedObjectData

DetectedObjectData::= SEQUENCE {
    detObjCommon    DetectedObjectCommonData,
    -- Common data for detected object
    detObjOptData   DetectedObjectOptionalData OPTIONAL
    -- Type specific optional data
}

DetectedObjectOptionalData ::= CHOICE {
    detVeh      DetectedVehicleData,
    -- Detected vehicle data
    detVRU      DetectedVRUData,
    -- Detected VRU data
    detObst     DetectedObstacleData
    -- Detected obstacle data
}

DetectedObjectCommonData::= SEQUENCE {
    objType             ObjectType,
    objTypeCfd          ClassificationConfidence,
    objectID            ObjectID,
    -- temporary ID assigned by source
    measurementTime     MeasurementTimeOffset,
    -- Detection time
    timeConfidence      TimeConfidence,
    pos                 PositionOffsetXYZ,
    posConfidence       PositionConfidenceSet,
    speed               Speed,
    speedConfidence     SpeedConfidence,
    speedZ              Speed OPTIONAL,
    speedConfidenceZ    SpeedConfidence OPTIONAL,
    heading             Heading,
    headingConf         HeadingConfidence,
    accel4way           AccelerationSet4Way OPTIONAL,
    accCfdX             AccelerationConfidence OPTIONAL,
    accCfdY             AccelerationConfidence OPTIONAL,
    accCfdZ             AccelerationConfidence OPTIONAL,
    accCfdYaw           YawRateConfidence OPTIONAL,
    ...
}

DetectedVehicleData::= SEQUENCE {
    lights                  ExteriorLights              OPTIONAL,
    vehAttitude             Attitude                    OPTIONAL,
    vehAttitudeConfidence   AttitudeConfidence          OPTIONAL,
    vehAngVel               AngularVelocity             OPTIONAL,
    vehAngVelConfidence     AngularVelocityConfidence   OPTIONAL,
    size                    VehicleSize                 OPTIONAL,
    height                  VehicleHeight               OPTIONAL,
    vehicleSizeConfidence   VehicleSizeConfidence       OPTIONAL,
    vehicleClass            BasicVehicleClass           OPTIONAL,
    classConf               ClassificationConfidence    OPTIONAL,
    ...
}

DetectedVRUData::= SEQUENCE {
    basicType       PersonalDeviceUserType  OPTIONAL,
    propulsion      PropelledInformation    OPTIONAL,
    attachment      Attachment              OPTIONAL,
    radius          AttachmentRadius        OPTIONAL
}

DetectedObstacleData::= SEQUENCE {
    obstSize            ObstacleSize,
    obstSizeConfidence  ObstacleSizeConfidence
}

ObjectType::= ENUMERATED{
    unknown (0),
    vehicle (1),
    vru     (2),
    animal  (3),
    ...
}

ObjectID ::= INTEGER (0..65535)

ClassificationConfidence ::= INTEGER (0..101)

MeasurementTimeOffset ::= INTEGER (-1500..1500) -- LSB units of 1ms

PositionOffsetXYZ ::= SEQUENCE {
    offsetX     ObjectDistance,
    offsetY     ObjectDistance,
    offsetZ     ObjectDistance OPTIONAL
}

ObjectDistance ::=INTEGER(-32767..32767) --LSB units of 0.1 meters

Attitude ::= SEQUENCE {
    pitch   PitchDetected,
    roll    RollDetected,
    yaw     YawDetected
}

PitchDetected ::= INTEGER (-7200..7200)
    -- LSB units of 0.0125 degrees (signed)
    -- range of -90 to 90 degrees

RollDetected ::= INTEGER (-14400..14400)
    -- LSB units of 0.0125 degrees (signed)
    -- range of -180 to 180 degrees

YawDetected ::= INTEGER (-14400..14400)
    -- LSB units of 0.0125 degrees (signed)
    -- range of -180 to 180 degrees

AttitudeConfidence ::= SEQUENCE {
    pitchConfidence     HeadingConfidence,
    rollConfidence      HeadingConfidence,
    yawConfidence       HeadingConfidence
}

AngularVelocity ::= SEQUENCE {
    pitchRate   SDSMPitchRate,
    rollRate    SDSMRollRate
}

SDSMPitchRate ::= INTEGER (-32767..32767)
    -- LSB units of 0.01 degrees per second (signed)
    -- unavailable (32767)

SDSMRollRate ::= INTEGER (-32767..32767)
    -- LSB units of 0.01 degrees per second (signed)
    -- unavailable (32767)

AngularVelocityConfidence ::= SEQUENCE {
    pitchRateConfidence PitchRateConfidence OPTIONAL,
    rollRateConfidence RollRateConfidence OPTIONAL
}

PitchRateConfidence ::= ENUMERATED {
    unavailable (0), -- B'000 Not Equipped with angular velocity status
    -- or angular velocity status is unavailable
    degSec-100-00 (1), -- B'001 100 deg/sec
    degSec-010-00 (2), -- B'010 10 deg/sec
    degSec-005-00 (3), -- B'011 5 deg/sec
    degSec-001-00 (4), -- B'100 1 deg/sec
    degSec-000-10 (5), -- B'101 0.1 deg/sec
    degSec-000-05 (6), -- B'110 0.05 deg/sec
    degSec-000-01 (7)  -- B'111 0.01 deg/sec
}

RollRateConfidence ::= ENUMERATED {
    unavailable (0), -- B'000 Not Equipped with angular velocity status
    -- or angular velocity status is unavailable
    degSec-100-00 (1), -- B'001 100 deg/sec
    degSec-010-00 (2), -- B'010 10 deg/sec
    degSec-005-00 (3), -- B'011 5 deg/sec
    degSec-001-00 (4), -- B'100 1 deg/sec
    degSec-000-10 (5), -- B'101 0.1 deg/sec
    degSec-000-05 (6), -- B'110 0.05 deg/sec
    degSec-000-01 (7)  -- B'111 0.01 deg/sec
}

VehicleSizeConfidence ::= SEQUENCE {
    vehicleWidthConfidence      SizeValueConfidence,
    vehicleLengthConfidence     SizeValueConfidence,
    vehicleHeightConfidence     SizeValueConfidence OPTIONAL
}

ObstacleSize ::= SEQUENCE {
    width   SizeValue,
    length  SizeValue,
    height  SizeValue   OPTIONAL
}

ObstacleSizeConfidence ::= SEQUENCE {
    widthConfidence     SizeValueConfidence,
    lengthConfidence    SizeValueConfidence,
    heightConfidence    SizeValueConfidence     OPTIONAL
}

SizeValue ::= INTEGER (0..1023) -- LSB units are 10 cm with a range of >100 meters

SizeValueConfidence ::= ENUMERATED {
    unavailable (0),
    size-100-00 (1),    -- (100 m)
    size-050-00 (2),    -- (50 m)
    size-020-00 (3),    -- (20 m)
    size-010-00 (4),    -- (10 m)
    size-005-00 (5),    -- (5 m)
    size-002-00 (6),    -- (2 m)
    size-001-00 (7),    -- (1 m)
    size-000-50 (8),    -- (50 cm)
    size-000-20 (9),    -- (20 cm)
    size-000-10 (10),   -- (10 cm)
    size-000-05 (11),   -- (5 cm)
    size-000-02 (12),   -- (2 cm)
    size-000-01 (13)    -- (1 cm)
}

END

-- Use of this module defined in SAE J2735
-- Latest document release for this module is Nov 2022
-- Filename: J2735-MessageFrame-2024-rel-v1.1.1.asn
--

MessageFrame
{joint-iso-itu-t (2) country (16) us (840) organization (1) sae (114566)
v2x-communications (1) technical-committees (1) v2x-core (5) technical-reports (1)
j2735 (2735) part-0 (0) asn1-module (1) messageFrame (1) version-1 (1) version-minor-1 (1)}

DEFINITIONS AUTOMATIC TAGS ::=
BEGIN

IMPORTS
    BasicSafetyMessage
        FROM BasicSafetyMessage {joint-iso-itu-t (2) country (16) us (840) organization (1) sae (114566)
        v2x-communications (1) technical-committees (1) v2x-core (5) technical-reports (1)
        j2735 (2735) part-0 (0) asn1-module (1) basicSafetyMessage (7)
      version-1 (1) version-minor-1 (1)}
    MapData
        FROM MapData {joint-iso-itu-t (2) country (16) us (840) organization (1) sae (114566)
        v2x-communications (1) technical-committees (1) v2x-core (5) technical-reports (1)
        j2735 (2735) part-0 (0) asn1-module (1) mapData (8)
      version-1 (1) version-minor-1 (1)}
    SPAT
        FROM SPAT {joint-iso-itu-t (2) country (16) us (840) organization (1) sae (114566)
        v2x-communications (1) technical-committees (1) v2x-core (5) technical-reports (1)
        j2735 (2735) part-0 (0) asn1-module (1) signalPhaseAndTimingMessage (9)
      version-1 (1) version-minor-1 (1)}
    CommonSafetyRequest
        FROM CommonSafetyRequest {joint-iso-itu-t (2) country (16) us (840) organization (1) sae (114566)
        v2x-communications (1) technical-committees (1) v2x-core (5) technical-reports (1)
        j2735 (2735) part-0 (0) asn1-module (1) commonSafetyRequest (10)
      version-1 (1) version-minor-1 (1)}
    EmergencyVehicleAlert
        FROM EmergencyVehicleAlert {joint-iso-itu-t (2) country (16) us (840) organization (1) sae (114566)
        v2x-communications (1) technical-committees (1) v2x-core (5) technical-reports (1)
        j2735 (2735) part-0 (0) asn1-module (1) emergencyVehicleAlert (11)
      version-1 (1) version-minor-1 (1)}
    IntersectionCollision
        FROM IntersectionCollision {joint-iso-itu-t (2) country (16) us (840) organization (1) sae (114566)
        v2x-communications (1) technical-committees (1) v2x-core (5) technical-reports (1)
        j2735 (2735) part-0 (0) asn1-module (1) intersectionCollision (12)
      version-1 (1) version-minor-1 (1)}
    NMEAcorrections
        FROM NMEAcorrections {joint-iso-itu-t (2) country (16) us (840) organization (1) sae (114566)
        v2x-communications (1) technical-committees (1) v2x-core (5) technical-reports (1)
        j2735 (2735) part-0 (0) asn1-module (1) nmeaCorrections (13)
      version-1 (1) version-minor-1 (1)}
    ProbeDataManagement
        FROM ProbeDataManagement {joint-iso-itu-t (2) country (16) us (840) organization (1) sae (114566)
        v2x-communications (1) technical-committees (1) v2x-core (5) technical-reports (1)
        j2735 (2735) part-0 (0) asn1-module (1) probeDataManagement (14)
      version-1 (1) version-minor-1 (1)}
    ProbeVehicleData
        FROM ProbeVehicleData {joint-iso-itu-t (2) country (16) us (840) organization (1) sae (114566)
        v2x-communications (1) technical-committees (1) v2x-core (5) technical-reports (1)
        j2735 (2735) part-0 (0) asn1-module (1) probeVehicleData (15)
      version-1 (1) version-minor-1 (1)}
    RoadSideAlert
        FROM RoadSideAlert {joint-iso-itu-t (2) country (16) us (840) organization (1) sae (114566)
        v2x-communications (1) technical-committees (1) v2x-core (5) technical-reports (1)
        j2735 (2735) part-0 (0) asn1-module (1) roadSideAlert (16)
      version-1 (1) version-minor-1 (1)}
    RTCMcorrections
        FROM RTCMcorrections {joint-iso-itu-t (2) country (16) us (840) organization (1) sae (114566)
        v2x-communications (1) technical-committees (1) v2x-core (5) technical-reports (1)
        j2735 (2735) part-0 (0) asn1-module (1) rtcmCorrections (17)
      version-1 (1) version-minor-1 (1)}
    SignalRequestMessage
        FROM SignalRequestMessage {joint-iso-itu-t (2) country (16) us (840) organization (1) sae (114566)
        v2x-communications (1) technical-committees (1) v2x-core (5) technical-reports (1)
        j2735 (2735) part-0 (0) asn1-module (1) signalRequestMessage (18)
      version-1 (1) version-minor-1 (1)}
    SignalStatusMessage
        FROM SignalStatusMessage {joint-iso-itu-t (2) country (16) us (840) organization (1) sae (114566)
        v2x-communications (1) technical-committees (1) v2x-core (5) technical-reports (1)
        j2735 (2735) part-0 (0) asn1-module (1) signalStatusMessage (19)
      version-1 (1) version-minor-1 (1)}
    TravelerInformation
        FROM TravelerInformation {joint-iso-itu-t (2) country (16) us (840) organization (1) sae (114566)
        v2x-communications (1) technical-committees (1) v2x-core (5) technical-reports (1)
        j2735 (2735) part-0 (0) asn1-module (1) travelerInformation (20)
      version-1 (1) version-minor-1 (1)}
    PersonalSafetyMessage
        FROM PersonalSafetyMessage {joint-iso-itu-t (2) country (16) us (840) organization (1) sae (114566)
        v2x-communications (1) technical-committees (1) v2x-core (5) technical-reports (1)
        j2735 (2735) part-0 (0) asn1-module (1) personalSafetyMessage (21)
      version-1 (1) version-minor-1 (1)}
    RoadSafetyMessage
        FROM RoadSafetyMessage {joint-iso-itu-t (2) country (16) us (840) organization (1) sae (114566)
      v2x-communications (1) technical-committees (1) v2x-core (5) technical-reports (1)
      j2945 (2945) slash-4 (4) asn1-module (1) roadSafetyMessage (39)
      version-1 (1) version-minor-1 (1)}
    RoadWeatherMessage
        FROM RoadWeatherMessage {joint-iso-itu-t (2) country (16) us (840) organization (1) sae (114566)
      v2x-communications (1) technical-committees (1) v2x-core (5) technical-reports (1)
      j2945 (2945) slash-3 (3) asn1-module (1) roadWeatherMessage (0)
      version-2 (2) version-minor-1 (1)}
    ProbeDataConfigMessage
        FROM ProbeDataConfig {joint-iso-itu-t (2) country (16) us (840) organization (1) sae (114566)
      v2x-communications (1) technical-committees (1) v2x-core (5) technical-reports (1)
      j2945 (2945) slash-c (12) asn1-module (1) probeDataConfig (0)
      version-1 (1) version-minor-1 (1)}
    ProbeDataReportMessage
        FROM ProbeDataReport {joint-iso-itu-t (2) country (16) us (840) organization (1) sae (114566)
      v2x-communications (1) technical-committees (1) v2x-core (5) technical-reports (1)
      j2945 (2945) slash-c (12) asn1-module (1) probeDataReport (1)
      version-1 (1) version-minor-1 (1)}
    TollAdvertisementMessage
        FROM TollAdvertisementMessage {joint-iso-itu-t (2) country (16) us (840) organization (1) sae (114566)
        v2x-communications (1) technical-committees (1) tolling-applications (9) technical-reports (1)
        j3217 (3217) asn1-module (1) tollAdvertisementMessage (0)
      version-1 (1) version-minor-1 (1)}
    TollUsageMessage
        FROM TollUsageMessage {joint-iso-itu-t (2) country (16) us (840) organization (1) sae (114566)
        v2x-communications (1) technical-committees (1) tolling-applications (9) technical-reports (1)
        j3217 (3217) asn1-module (1) tollUsageMessage (1)
      version-1 (1) version-minor-1 (1)}
    TollUsageAckMessage
        FROM TollUsageAckMessage {joint-iso-itu-t (2) country (16) us (840) organization (1) sae (114566)
        v2x-communications (1) technical-committees (1) tolling-applications (9) technical-reports (1)
        j3217 (3217) asn1-module (1) tollUsageAckMessage (2)
      version-1 (1) version-minor-1 (1)}
    CooperativeControlMessage
        FROM CooperativeControlMessage {joint-iso-itu-t (2) country (16) us (840) organization (1) sae (114566)
      v2x-communications (1) technical-committees (1) v2x-vehicular-applications (8) technical-reports (1)
      j2945 (2945) slash-6 (6) asn1-module (1) cooperativeControlMessage (40)
      version-1 (1) version-minor-1 (1)}
    SensorDataSharingMessage
        FROM SensorDataSharingMessage {joint-iso-itu-t (2) country (16) us (840) organization (1) sae (114566)
        v2x-communications (1) technical-committees (1) v2x-vehicular-applications (8) technical-reports (1)
      j3224 (3224) asn1-module (1) sensorDataSharingMessage (41)
      version-1 (1) version-minor-1 (1)}
    ManeuverSharingAndCoordinatingMessage
        FROM ManeuverSharingAndCoordinatingMessage {joint-iso-itu-t (2) country (16) us (840) organization (1) sae (114566)
      v2x-communications (1) technical-committees (1) v2x-vehicular-applications (8) technical-reports (1)
      j3186 (3186) asn1-module (1) maneuverSharingAndCoordinatingMessage (42)
      version-1 (1) version-minor-1 (1)}
    RoadGeometryAndAttributes
        FROM RoadGeometryAndAttributes {joint-iso-itu-t (2) country (16) us (840) organization (1) sae (114566)
      v2x-communications (1) technical-committees (1) v2x-core (5) technical-reports (1)
      j2945 (2945) slash-a (10) asn1-module (1) roadGeometryAndAttributes (43)
      version-1 (1) version-minor-1 (1)}
    PersonalSafetyMessage2
        FROM PersonalSafetyMessage2 {joint-iso-itu-t (2) country (16) us (840) organization (1) sae (114566)
      v2x-communications (1) technical-committees (1) v2x-vehicular-applications (8) technical-reports (1)
      j2945 (2945) slash-9 (9) asn1-module (1) personalSafetyMessage2 (44)
      version-1 (1) version-minor-1 (1)}
   TrafficSignalPhaseAndTiming
      FROM TrafficSignalPhaseAndTiming {joint-iso-itu-t (2) country (16) us (840) organization (1) sae (114566)
      v2x-communications (1) technical-committees (1) v2x-core (5) technical-reports (1)
      j2735 (2735) part-0 (0) asn1-module (1) trafficSignalPhaseAndTiming (45)
      version-1 (1) version-minor-1 (1)}
   SignalControlAndPrioritizationRequest
      FROM SignalControlAndPrioritizationRequest {joint-iso-itu-t (2) country (16) us (840) organization (1) sae (114566)
      v2x-communications (1) technical-committees (1) v2x-core (5) technical-reports (1)
      j2735 (2735) part-0 (0) asn1-module (1) signalControlAndPrioritizationRequest (46)
      version-1 (1) version-minor-1 (1)}
   SignalControlAndPrioritizationStatus
      FROM SignalControlAndPrioritizationStatus {joint-iso-itu-t (2) country (16) us (840) organization (1) sae (114566)
      v2x-communications (1) technical-committees (1) v2x-core (5) technical-reports (1)
      j2735 (2735) part-0 (0) asn1-module (1) signalControlAndPrioritizationStatus (47)
      version-1 (1) version-minor-1 (1)}
   RoadUserChargingConfigMessage
      FROM RoadUserChargingConfigMessage {joint-iso-itu-t (2) country (16) us (840) organization (1) sae (114566)
      v2x-communications (1) technical-committees (1) tolling-applications (9) technical-reports (1)
      j3217 (3217) slash-r (28) asn1-module (1) roadUserChargingConfigMessage (3)
      version-1 (1) version-minor-1 (1)}
   RoadUserChargingReportMessage
      FROM RoadUserChargingReportMessage {joint-iso-itu-t (2) country (16) us (840) organization (1) sae (114566)
      v2x-communications (1) technical-committees (1) tolling-applications (9) technical-reports (1)
      j3217 (3217) slash-r (28) asn1-module (1) roadUserChargingReportMessage (4)
      version-1 (1) version-minor-1 (1)}
   TrafficLightStatusMessage
      FROM TrafficLightStatusMessage {joint-iso-itu-t (2) country (16) us (840) organization (1) sae (114566)
        v2x-communications (1) technical-committees (1) v2x-core (5) technical-reports (1)
        j2735 (2735) part-0 (0) asn1-module (1) trafficLightStatusMessage (50)
        version-1 (1) version-minor-1 (1)}
    TestMessage00
        FROM TestMessage00 {joint-iso-itu-t (2) country (16) us (840) organization (1) sae (114566)
        v2x-communications (1) technical-committees (1) v2x-core (5) technical-reports (1)
        j2735 (2735) part-0 (0) asn1-module (1) testMessage00 (22)
      version-1 (1) version-minor-1 (1)}
    TestMessage01
        FROM TestMessage01 {joint-iso-itu-t (2) country (16) us (840) organization (1) sae (114566)
        v2x-communications (1) technical-committees (1) v2x-core (5) technical-reports (1)
        j2735 (2735) part-0 (0) asn1-module (1) testMessage01 (23)
      version-1 (1) version-minor-1 (1)}
    TestMessage02
        FROM TestMessage02 {joint-iso-itu-t (2) country (16) us (840) organization (1) sae (114566)
        v2x-communications (1) technical-committees (1) v2x-core (5) technical-reports (1)
        j2735 (2735) part-0 (0) asn1-module (1) testMessage02 (24)
      version-1 (1) version-minor-1 (1)}
    TestMessage03
        FROM TestMessage03 {joint-iso-itu-t (2) country (16) us (840) organization (1) sae (114566)
        v2x-communications (1) technical-committees (1) v2x-core (5) technical-reports (1)
        j2735 (2735) part-0 (0) asn1-module (1) testMessage03 (25)
      version-1 (1) version-minor-1 (1)}
    TestMessage04
        FROM TestMessage04 {joint-iso-itu-t (2) country (16) us (840) organization (1) sae (114566)
        v2x-communications (1) technical-committees (1) v2x-core (5) technical-reports (1)
        j2735 (2735) part-0 (0) asn1-module (1) testMessage04 (26)
      version-1 (1) version-minor-1 (1)}
    TestMessage05
        FROM TestMessage05 {joint-iso-itu-t (2) country (16) us (840) organization (1) sae (114566)
        v2x-communications (1) technical-committees (1) v2x-core (5) technical-reports (1)
        j2735 (2735) part-0 (0) asn1-module (1) testMessage05 (27)
      version-1 (1) version-minor-1 (1)}
    TestMessage06
        FROM TestMessage06 {joint-iso-itu-t (2) country (16) us (840) organization (1) sae (114566)
        v2x-communications (1) technical-committees (1) v2x-core (5) technical-reports (1)
        j2735 (2735) part-0 (0) asn1-module (1) testMessage06 (28)
      version-1 (1) version-minor-1 (1)}
    TestMessage07
        FROM TestMessage07 {joint-iso-itu-t (2) country (16) us (840) organization (1) sae (114566)
        v2x-communications (1) technical-committees (1) v2x-core (5) technical-reports (1)
        j2735 (2735) part-0 (0) asn1-module (1) testMessage07 (29)
      version-1 (1) version-minor-1 (1)}
    TestMessage08
        FROM TestMessage08 {joint-iso-itu-t (2) country (16) us (840) organization (1) sae (114566)
        v2x-communications (1) technical-committees (1) v2x-core (5) technical-reports (1)
        j2735 (2735) part-0 (0) asn1-module (1) testMessage08 (30)
      version-1 (1) version-minor-1 (1)}
    TestMessage09
        FROM TestMessage09 {joint-iso-itu-t (2) country (16) us (840) organization (1) sae (114566)
        v2x-communications (1) technical-committees (1) v2x-core (5) technical-reports (1)
        j2735 (2735) part-0 (0) asn1-module (1) testMessage09 (31)
      version-1 (1) version-minor-1 (1)}
    TestMessage10
        FROM TestMessage10 {joint-iso-itu-t (2) country (16) us (840) organization (1) sae (114566)
        v2x-communications (1) technical-committees (1) v2x-core (5) technical-reports (1)
        j2735 (2735) part-0 (0) asn1-module (1) testMessage10 (32)
      version-1 (1) version-minor-1 (1)}
    TestMessage11
        FROM TestMessage11 {joint-iso-itu-t (2) country (16) us (840) organization (1) sae (114566)
        v2x-communications (1) technical-committees (1) v2x-core (5) technical-reports (1)
        j2735 (2735) part-0 (0) asn1-module (1) testMessage11 (33)
      version-1 (1) version-minor-1 (1)}
    TestMessage12
        FROM TestMessage12 {joint-iso-itu-t (2) country (16) us (840) organization (1) sae (114566)
        v2x-communications (1) technical-committees (1) v2x-core (5) technical-reports (1)
        j2735 (2735) part-0 (0) asn1-module (1) testMessage12 (34)
      version-1 (1) version-minor-1 (1)}
    TestMessage13
        FROM TestMessage13 {joint-iso-itu-t (2) country (16) us (840) organization (1) sae (114566)
        v2x-communications (1) technical-committees (1) v2x-core (5) technical-reports (1)
        j2735 (2735) part-0 (0) asn1-module (1) testMessage13 (35)
      version-1 (1) version-minor-1 (1)}
    TestMessage14
        FROM TestMessage14 {joint-iso-itu-t (2) country (16) us (840) organization (1) sae (114566)
        v2x-communications (1) technical-committees (1) v2x-core (5) technical-reports (1)
        j2735 (2735) part-0 (0) asn1-module (1) testMessage14 (36)
      version-1 (1) version-minor-1 (1)}
    TestMessage15
        FROM TestMessage15 {joint-iso-itu-t (2) country (16) us (840) organization (1) sae (114566)
        v2x-communications (1) technical-committees (1) v2x-core (5) technical-reports (1)
        j2735 (2735) part-0 (0) asn1-module (1) testMessage15 (37)
      version-1 (1) version-minor-1 (1)};


-- -_-_-_-_-_-_-_-_-_-_-_-_-_-_-_-_-_-_-_-_-_-_-_-_-_-_-_-_
--
-- Start of entries from table Messages...
-- This table typically contains message entries.
-- -_-_-_-_-_-_-_-_-_-_-_-_-_-_-_-_-_-_-_-_-_-_-_-_-_-_-_-_
--

MessageFrame ::= SEQUENCE {
   messageId   MESSAGE-ID-AND-TYPE.&id({MessageTypes}),
   value       MESSAGE-ID-AND-TYPE.&Type({MessageTypes}{@.messageId}),
   ...
   }

MESSAGE-ID-AND-TYPE ::= CLASS {
   &id    DSRCmsgID UNIQUE,
   &Type
   } WITH SYNTAX {&Type IDENTIFIED BY &id}

MessageTypes MESSAGE-ID-AND-TYPE ::= {
   { BasicSafetyMessage                     IDENTIFIED BY basicSafetyMessage    } |
   { MapData                                IDENTIFIED BY mapData               } |
   { SPAT                                   IDENTIFIED BY signalPhaseAndTimingMessage } |
   { CommonSafetyRequest                    IDENTIFIED BY commonSafetyRequest   } |
   { EmergencyVehicleAlert                  IDENTIFIED BY emergencyVehicleAlert } |
   { IntersectionCollision                  IDENTIFIED BY intersectionCollision } |
   { NMEAcorrections                        IDENTIFIED BY nmeaCorrections       } |
   { ProbeDataManagement                    IDENTIFIED BY probeDataManagement   } |
   { ProbeVehicleData                       IDENTIFIED BY probeVehicleData      } |
   { RoadSideAlert                          IDENTIFIED BY roadSideAlert         } |
   { RTCMcorrections                        IDENTIFIED BY rtcmCorrections       } |
   { SignalRequestMessage                   IDENTIFIED BY signalRequestMessage  } |
   { SignalStatusMessage                    IDENTIFIED BY signalStatusMessage   } |
   { TravelerInformation                    IDENTIFIED BY travelerInformation   } |
   { PersonalSafetyMessage                  IDENTIFIED BY personalSafetyMessage } |
   { RoadSafetyMessage                      IDENTIFIED BY roadSafetyMessage     } |
   { RoadWeatherMessage                     IDENTIFIED BY roadWeatherMessage    } |
   { ProbeDataConfigMessage                 IDENTIFIED BY probeDataConfigMessage                } |
   { ProbeDataReportMessage                 IDENTIFIED BY probeDataReportMessage                } |
   { TollAdvertisementMessage               IDENTIFIED BY tollAdvertisementMessage              } |
   { TollUsageMessage                       IDENTIFIED BY tollUsageMessage                      } |
   { TollUsageAckMessage                    IDENTIFIED BY tollUsageAckMessage                   } |
   { CooperativeControlMessage              IDENTIFIED BY cooperativeControlMessage             } |
   { SensorDataSharingMessage               IDENTIFIED BY sensorDataSharingMessage              } |
   { ManeuverSharingAndCoordinatingMessage  IDENTIFIED BY maneuverSharingAndCoordinatingMessage } |
   { RoadGeometryAndAttributes              IDENTIFIED BY roadGeometryAndAttributes             } |
   { PersonalSafetyMessage2                 IDENTIFIED BY personalSafetyMessage2                } |
   { TrafficSignalPhaseAndTiming            IDENTIFIED BY trafficSignalPhaseAndTiming           } |
   { SignalControlAndPrioritizationRequest  IDENTIFIED BY signalControlAndPrioritizationRequest } |
   { SignalControlAndPrioritizationStatus   IDENTIFIED BY signalControlAndPrioritizationStatus  } |
   { RoadUserChargingConfigMessage         IDENTIFIED BY roadUserChargingConfigMessage        } |
   { RoadUserChargingReportMessage         IDENTIFIED BY roadUserChargingReportMessage        } |
   { TrafficLightStatusMessage            IDENTIFIED BY trafficLightStatusMessage            } |
   { TestMessage00                          IDENTIFIED BY testMessage00 } |
   { TestMessage01                          IDENTIFIED BY testMessage01 } |
   { TestMessage02                          IDENTIFIED BY testMessage02 } |
   { TestMessage03                          IDENTIFIED BY testMessage03 } |
   { TestMessage04                          IDENTIFIED BY testMessage04 } |
   { TestMessage05                          IDENTIFIED BY testMessage05 } |
   { TestMessage06                          IDENTIFIED BY testMessage06 } |
   { TestMessage07                          IDENTIFIED BY testMessage07 } |
   { TestMessage08                          IDENTIFIED BY testMessage08 } |
   { TestMessage09                          IDENTIFIED BY testMessage09 } |
   { TestMessage10                          IDENTIFIED BY testMessage10 } |
   { TestMessage11                          IDENTIFIED BY testMessage11 } |
   { TestMessage12                          IDENTIFIED BY testMessage12 } |
   { TestMessage13                          IDENTIFIED BY testMessage13 } |
   { TestMessage14                          IDENTIFIED BY testMessage14 } |
   { TestMessage15                          IDENTIFIED BY testMessage15 } ,
   ... -- Expansion to be used only by the SAE V2X Core TC
   }

DSRCmsgID ::= INTEGER (0..32767)

   --
   -- UPER forms
   --
   mapData                                  DSRCmsgID ::=   18 -- MAP, intersections
   signalPhaseAndTimingMessage              DSRCmsgID ::=   19 -- SPAT
   -- Above two entries were adopted in the 2015-04 edition
   -- Message assignments added in 2015 follow below
   basicSafetyMessage                       DSRCmsgID ::=   20 -- BSM, heartbeat msg
   commonSafetyRequest                      DSRCmsgID ::=   21 -- CSR
   emergencyVehicleAlert                    DSRCmsgID ::=   22 -- EVA
   intersectionCollision                    DSRCmsgID ::=   23 -- ICA
   nmeaCorrections                          DSRCmsgID ::=   24 -- NMEA
   probeDataManagement                      DSRCmsgID ::=   25 -- PDM
   probeVehicleData                         DSRCmsgID ::=   26 -- PVD
   roadSideAlert                            DSRCmsgID ::=   27 -- RSA
   rtcmCorrections                          DSRCmsgID ::=   28 -- RTCM
   signalRequestMessage                     DSRCmsgID ::=   29 -- SRM
   signalStatusMessage                      DSRCmsgID ::=   30 -- SSM
   travelerInformation                      DSRCmsgID ::=   31 -- TIM
   personalSafetyMessage                    DSRCmsgID ::=   32 -- PSM
   roadSafetyMessage                        DSRCmsgID ::=   33 -- RSM
   roadWeatherMessage                       DSRCmsgID ::=   34 -- RWM
   probeDataConfigMessage                   DSRCmsgID ::=   35 -- PDC
   probeDataReportMessage                   DSRCmsgID ::=   36 -- PDR
   tollAdvertisementMessage                 DSRCmsgID ::=   37 -- TAM
   tollUsageMessage                         DSRCmsgID ::=   38 -- TUM
   tollUsageAckMessage                      DSRCmsgID ::=   39 -- TUMack
   cooperativeControlMessage                DSRCmsgID ::=   40 -- CCM
   sensorDataSharingMessage                 DSRCmsgID ::=   41 -- SDSM
   maneuverSharingAndCoordinatingMessage    DSRCmsgID ::=   42 -- MSCM
   roadGeometryAndAttributes                DSRCmsgID ::=   43 -- RGA
   personalSafetyMessage2                   DSRCmsgID ::=   44 -- PSM2
   trafficSignalPhaseAndTiming              DSRCmsgID ::=   45 -- TSPaT
   signalControlAndPrioritizationRequest    DSRCmsgID ::=   46 -- SCPR
   signalControlAndPrioritizationStatus     DSRCmsgID ::=   47 -- SCPS
   roadUserChargingConfigMessage          DSRCmsgID ::=   48 -- RUCCM
   roadUserChargingReportMessage          DSRCmsgID ::=   49 -- RUCRM
   trafficLightStatusMessage            DSRCmsgID ::=   50 -- TLSM

   --
   -- The Below values are reserved for local message testing use
   --
   testMessage00                     DSRCmsgID ::=  240 -- Hex 0xF0
   testMessage01                     DSRCmsgID ::=  241
   testMessage02                     DSRCmsgID ::=  242
   testMessage03                     DSRCmsgID ::=  243
   testMessage04                     DSRCmsgID ::=  244
   testMessage05                     DSRCmsgID ::=  245
   testMessage06                     DSRCmsgID ::=  246
   testMessage07                     DSRCmsgID ::=  247
   testMessage08                     DSRCmsgID ::=  248
   testMessage09                     DSRCmsgID ::=  249
   testMessage10                     DSRCmsgID ::=  250
   testMessage11                     DSRCmsgID ::=  251
   testMessage12                     DSRCmsgID ::=  252
   testMessage13                     DSRCmsgID ::=  253
   testMessage14                     DSRCmsgID ::=  254
   testMessage15                     DSRCmsgID ::=  255-- Hex 0xFF
   --
   -- All other values are reserved for std use
   --
END
